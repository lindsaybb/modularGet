/*
 * This YANG module has been generated by smidump 0.5.0:
 *
 *      smidump -f yang ISKRATEL-MSAN-MIB
 *
 * Do not edit. Edit the source file instead!
 */

/*
 * WARNING: this output may be incorrect due to significant parse errors
 */

module ISKRATEL-MSAN-MIB {

  namespace "urn:ietf:params:xml:ns:yang:smiv2:ISKRATEL-MSAN-MIB";
  prefix "iskratel-msan";

  import BRIDGE-MIB {
    prefix "bridge-mib";
  }

  import IF-MIB {
    prefix "if-mib";
  }

  import INET-ADDRESS-MIB {
    prefix "inet-address";
  }

  import Q-BRIDGE-MIB {
    prefix "q-bridge";
  }

  import RFC1155-SMI {
    prefix "rfc1155-smi";
  }

  import RFC1213-MIB {
    prefix "rfc1213-mib";
  }

  import SNMP-FRAMEWORK-MIB {
    prefix "snmp-framework";
  }

  import SNMPv2-TC {
    prefix "snmpv2-tc";
  }

  import VDSL-LINE-MIB {
    prefix "vdsl-line";
  }

  import VDSL2-LINE-MIB {
    prefix "vdsl2-line";
  }

  import ietf-inet-types {
    prefix "inet";
  }

  import ietf-yang-smiv2 {
    prefix "smiv2";
  }

  import ietf-yang-types {
    prefix "yang";
  }
  
  import ietf-interfaces {
    prefix "if";
  }

  organization
   "Iskratel";

  contact
   "Contact-info.";

  description
   "Description.";

  revision 2010-06-22 {
    description
     "[Revision added by libsmi due to a LAST-UPDATED clause.]";
  }

  typedef VlanList {
    type binary;
    description
     "Each octet within this value specifies a set of eight
      vlans, with the first octet specifying vlans 1 through
      8, the second octet specifying vlans 9 through 16, etc.
      Within each octet, the most significant bit represents
      the lowest numbered vlan, and the least significant bit
      represents the highest numbered vlan.  Thus, each vlan
      supported is represented by a single bit within the
      value of this object.  If that bit has a value of '1'
      then the associated port is in that vlan; the port is
      not included if the vlans bit has a value of '0'.";
  }

  typedef Xdsl2PsdMaskDs {
    type binary {
      length "0..96";
    }
    description
     "This is a structure that represents up to 32 PSD mask
      breakpoints.
      Each breakpoint occupies 3 octets: The first
      two octets hold the index of the subcarrier associated with the
      breakpoint.  The third octet holds the PSD reduction at the
      breakpoint from 0 (0 dBm/Hz) to 255 (-127.5 dBm/Hz) using units
      of 0.5 dBm/Hz.
      The subcarrier index is an unsigned number in the range 0 to
      NSCds-1.";
  }

  typedef Xdsl2PsdMaskUs {
    type binary {
      length "0..48";
    }
    description
     "This is a structure that represents up to 16 PSD mask breakpoints.
      Each breakpoint occupies 3 octets: The first two octets hold the
      index of the subcarrier associated with the breakpoint.
      The third octet holds the PSD reduction at the breakpoint from
      0(0 dBm/Hz) to 255 (-127.5 dBm/Hz) using units of 0.5 dBm/Hz.
      The subcarrier index is an unsigned number in the range 0 to NSCus-1.";
  }

  typedef PortMask {
    type binary;
    description
     "Each octet within this value specifies a set of eight
      ports, with the first octet specifying ports 1 through
      8, the second octet specifying ports 9 through 16, etc.
      Within each octet, the most significant bit represents
      the lowest numbered port, and the least significant bit
      represents the highest numbered port.  Thus, each port
      of the bridge is represented by a single bit within the
      value of this object.  If that bit has a value of '1'
      then that port is included in the set of ports; the port
      is not included if its bit has a value of '0'
      
      When setting this value, the system will ignore
      configuration for ports not between the first and last
      valid ports.  Configuration of any port numbers between
      this range that are not valid ports return a failure
      message, but will still apply configuration for valid
      ports.";
  }

  typedef PercentByFives {
    type uint32 {
      range "0|5|10|15|20|25|30|35|40|45|50|55|60|65|70|75|80|85|90|95|100";
    }
    description
     "An unsigned integer representing a value expressed
      as a percentage with five percent increments.";
  }


  container ISKRATEL-MSAN-MIB {
    config true;

    container msanShelfInfo {
            config false;

      smiv2:oid 1.3.6.1.4.1.1332.1.1.5.1.1;

      leaf msanShelfId {
        type binary;
        description
         "MSAN shelf ID.";
        smiv2:max-access read-only;
        smiv2:oid 1.3.6.1.4.1.1332.1.1.5.1.1.1;
      }

      leaf msanShelfType {
        type binary;
        description
         "MSAN shelf type.";
        smiv2:max-access read-only;
        smiv2:oid 1.3.6.1.4.1.1332.1.1.5.1.1.2;
      }

      leaf msanShelfSize {
        type int32;
        description
         "Size of MSAN shelf (in number of slots).";
        smiv2:max-access read-only;
        smiv2:oid 1.3.6.1.4.1.1332.1.1.5.1.1.3;
      }
    }

    container msanSwInfo {
            config false;

      smiv2:oid 1.3.6.1.4.1.1332.1.1.5.1.3;

      leaf msanSwSteerVersion {
        type rfc1213-mib:DisplayString;
        description
         "The unique steer code for this software. ";
        smiv2:max-access read-only;
        smiv2:oid 1.3.6.1.4.1.1332.1.1.5.1.3.1;
      }

      leaf msanSwBuildDirectory {
        type rfc1213-mib:DisplayString;
        description
         "The directory where software was build on. ";
        smiv2:max-access read-only;
        smiv2:oid 1.3.6.1.4.1.1332.1.1.5.1.3.2;
      }

      leaf msanSwBuildTime {
        type rfc1213-mib:DisplayString;
        description
         "The time when the software was built.  (DateAndTime textual convention, from SNMPv2-TC)";
        smiv2:max-access read-only;
        smiv2:oid 1.3.6.1.4.1.1332.1.1.5.1.3.3;
      }

      leaf msanSwBranch {
        type rfc1213-mib:DisplayString;
        description
         "The repository branch where the software was built from.";
        smiv2:max-access read-only;
        smiv2:oid 1.3.6.1.4.1.1332.1.1.5.1.3.4;
      }

      leaf msanSwBuildReference {
        type int32;
        description
         "The repository reference number of the software build branch. ";
        smiv2:max-access read-only;
        smiv2:oid 1.3.6.1.4.1.1332.1.1.5.1.3.5;
      }

      leaf msanSwILVersion {
        type rfc1213-mib:DisplayString;
        description
         "The unique IL steer code for this software. ";
        smiv2:max-access read-only;
        smiv2:oid 1.3.6.1.4.1.1332.1.1.5.1.3.6;
      }

      leaf msanSwIpmiVersion {
        type rfc1213-mib:DisplayString;
        description
         "The major version.minor version/IPMI version supported(HEX) number of the IPMI currently running on the switch.
          For example, if the major version was 1 and the minor version was 2, the format would be '1.2/0'.";
        smiv2:max-access read-only;
        smiv2:oid 1.3.6.1.4.1.1332.1.1.5.1.3.7;
      }

      leaf msanSwBspVersion {
        type rfc1213-mib:DisplayString;
        description
         "The release.version/id number of the BSP software currently running on the switch.
          For example, if the release was 1 and the version was 2, the format would be '1.2/0'.";
        smiv2:max-access read-only;
        smiv2:oid 1.3.6.1.4.1.1332.1.1.5.1.3.8;
      }

      leaf msanSwCPLDVersion {
        type rfc1213-mib:DisplayString;
        description
         "CPLD (Complex Programmable Logic Device) SW version";
        smiv2:max-access read-only;
        smiv2:oid 1.3.6.1.4.1.1332.1.1.5.1.3.9;
      }

      leaf msanReservePackage {
        type rfc1213-mib:DisplayString;
        description
         "Name of the reserve package on disk if it exists. ";
        smiv2:max-access read-only;
        smiv2:oid 1.3.6.1.4.1.1332.1.1.5.1.3.10;
      }
    }

    container msanOtherInfo {
            config false;

      smiv2:oid 1.3.6.1.4.1.1332.1.1.5.1.4;

      leaf msanSnmpSetErrorReason {
        type rfc1213-mib:DisplayString;
        description
         "Last error description of SNMP set command.";
        smiv2:max-access read-only;
        smiv2:oid 1.3.6.1.4.1.1332.1.1.5.1.4.1;
      }
    }

    container msanLicenseGlobal {
            config true;

      smiv2:oid 1.3.6.1.4.1.1332.1.1.5.1.5.1;

      leaf msanLicenseId {
        type rfc1213-mib:DisplayString;
                config false;

        description
         "License ID.";
        smiv2:max-access read-only;
        smiv2:oid 1.3.6.1.4.1.1332.1.1.5.1.5.1.1;
      }

      leaf msanLicenseCreationDate {
        type rfc1213-mib:DisplayString;
                config false;

        description
         "Licence creation date.";
        smiv2:max-access read-only;
        smiv2:oid 1.3.6.1.4.1.1332.1.1.5.1.5.1.2;
      }

      leaf msanLicenseExpirationDate {
        type rfc1213-mib:DisplayString;
                config false;

        description
         "Licence expiration date.";
        smiv2:max-access read-only;
        smiv2:oid 1.3.6.1.4.1.1332.1.1.5.1.5.1.3;
      }

      leaf msanLicenseCustomerId {
        type rfc1213-mib:DisplayString;
                config false;

        description
         "License customer  ID.";
        smiv2:max-access read-only;
        smiv2:oid 1.3.6.1.4.1.1332.1.1.5.1.5.1.4;
      }

      leaf msanLicenseActivate {
        type enumeration {
          enum enable {
            value 1;
          }
          enum disable {
            value 2;
          }
        }
                config true;

        description
         "Activate licence files from local disk.";
        smiv2:max-access read-write;
        smiv2:oid 1.3.6.1.4.1.1332.1.1.5.1.5.1.5;
      }

      leaf msanLicenseFileGet {
        type rfc1213-mib:DisplayString;
        description
         "msanLicenseFileGet parameter is used to start transfer of  license file (extension .lic) from external tftp or ftp server to local file.
          Next syntax must be used for tftp or ftp transfer:
          tftp://<IP>|<hostname>[:<port>]/[<path>/]<remote_file_name> [<local_file_name>]
          ftp://<usr>[:<pass>]@<IP>|<hostname>[:<port>]/[<path>/]<remote_file_name>  [<local_file_name>]";
        smiv2:defval "";
        smiv2:max-access read-write;
        smiv2:oid 1.3.6.1.4.1.1332.1.1.5.1.5.1.6;
      }
    }

    container msanCpu {
            config false;

      smiv2:oid 1.3.6.1.4.1.1332.1.1.5.1.6.1;

      leaf msanCpuCurUsage {
        type int32 {
          range "0..100";
        }
        units Percent;
        description
         "Current CPU Usage in the last 10 sec.";
        smiv2:max-access read-only;
        smiv2:oid 1.3.6.1.4.1.1332.1.1.5.1.6.1.1;
      }

      leaf msanCpuMaxUsage {
        type int32 {
          range "0..100";
        }
        units Percent;
        description
         "Maximum CPU Usage.";
        smiv2:max-access read-only;
        smiv2:oid 1.3.6.1.4.1.1332.1.1.5.1.6.1.2;
      }

      leaf msanCpuMinUsage {
        type int32 {
          range "0..100";
        }
        units Percent;
        description
         "Minimum CPU Usage.";
        smiv2:max-access read-only;
        smiv2:oid 1.3.6.1.4.1.1332.1.1.5.1.6.1.3;
      }

      leaf msanCpuAvgUsage {
        type int32 {
          range "0..100";
        }
        units Percent;
        description
         "Average CPU Usage.";
        smiv2:max-access read-only;
        smiv2:oid 1.3.6.1.4.1.1332.1.1.5.1.6.1.4;
      }
    }

    container msanMemory {
            config false;

      smiv2:oid 1.3.6.1.4.1.1332.1.1.5.1.6.3;

      leaf msanMemoryTotal {
        type uint32;
        units kB;
        description
         "Description.";
        smiv2:max-access read-only;
        smiv2:oid 1.3.6.1.4.1.1332.1.1.5.1.6.3.1;
      }

      leaf msanMemoryFree {
        type uint32;
        units kB;
        description
         "Description.";
        smiv2:max-access read-only;
        smiv2:oid 1.3.6.1.4.1.1332.1.1.5.1.6.3.2;
      }

      leaf msanMemoryAllocated {
        type uint32;
        units kB;
        description
         "Description.";
        smiv2:max-access read-only;
        smiv2:oid 1.3.6.1.4.1.1332.1.1.5.1.6.3.3;
      }
    }

    container msanSystem {
            config true;

      smiv2:oid 1.3.6.1.4.1.1332.1.1.5.3.1;

      leaf msanDateTime {
        type binary;
        description
         "Board date and time in format: dd/MM/yyyy HH:mm:ss.";
        smiv2:max-access read-write;
        smiv2:oid 1.3.6.1.4.1.1332.1.1.5.3.1.1;
      }

      leaf msanShelfIdConf {
        type binary;
        description
         "MSAN Shelf ID.";
        smiv2:max-access read-write;
        smiv2:oid 1.3.6.1.4.1.1332.1.1.5.3.1.2;
      }

      leaf msanConfData {
        type enumeration {
          enum saved {
            value 1;
          }
          enum notSaved {
            value 2;
          }
        }
                config false;

        description
         "Configured data saved or not saved to file on local file system.";
        smiv2:max-access read-only;
        smiv2:oid 1.3.6.1.4.1.1332.1.1.5.3.1.3;
      }

      leaf msanSwUpgrade {
        type binary;
        status deprecated;
        description
         "msanSWUpgrade parameetr is used to start SW upgrade from external http or ftp server.
          User must set the next string value:         <repository URL> <package name> [|reboot|]
          
          <repository URL> = http|ftp://<IP>|<hostname>[:<port>]/[<path>/]
          
          
          Procedure uses anonymous type of identification.
          If a non standard port is used, this port must be also specified in the repository URL.
          'reboot' option is used only on boards with multiple SW packages support.";
        smiv2:max-access read-write;
        smiv2:oid 1.3.6.1.4.1.1332.1.1.5.3.1.4;
      }

      leaf msanCliScriptCreate {
        type binary {
          length "0..32";
        }
        description
         "When set with a non-empty string, current configuration will be saved to script file with that name
          (name must end with .scr).
          If file already exists it's overwritten.
          On Get request this object will always return an empty string.";
        smiv2:max-access read-write;
        smiv2:oid 1.3.6.1.4.1.1332.1.1.5.3.1.5;
      }

      leaf msanCliPrompt {
        type binary {
          length "0..64";
        }
        description
         "CLI prompt value.";
        smiv2:max-access read-write;
        smiv2:oid 1.3.6.1.4.1.1332.1.1.5.3.1.7;
      }

      leaf msanChassisId {
        type int32 {
          range "1..99";
        }
        description
         "MSAN Chassis ID.";
        smiv2:max-access read-write;
        smiv2:oid 1.3.6.1.4.1.1332.1.1.5.3.1.8;
      }

      leaf msanConfFileType {
        type enumeration {
          enum automatic {
            value 1;
          }
          enum manual {
            value 2;
          }
          enum notExists {
            value 3;
          }
          enum manualMns {
            value 4;
          }
        }
                config false;

        description
         "Last saved configuration status � denotes whether current configuration file
          has been built by automatic or manual cli/snmp or manual mns procedure. ";
        smiv2:max-access read-only;
        smiv2:oid 1.3.6.1.4.1.1332.1.1.5.3.1.13;
      }
    }

    container msanSystemSwUpgrade {
            config false;
            description 
                "This is System SW Upgrade info table.
                 For upgrade action see rpc definition systemSwUpgrade";

      smiv2:oid 1.3.6.1.4.1.1332.1.1.5.3.1.10;

      leaf msanSystemSwUpgradeStatus {
        type enumeration {
          enum inprogress {
            value 1;
          }
          enum successful {
            value 2;
          }
          enum failed {
            value 3;
          }
          enum notInitiated {
            value 4;
          }
        }
                config false;

        description
         "The SW upgrade status info.";
        smiv2:defval notInitiated;
        smiv2:max-access read-only;
        smiv2:oid 1.3.6.1.4.1.1332.1.1.5.3.1.10.2;
      }

      leaf msanSystemSwUpgradeStatusAddInfo {
        type rfc1213-mib:DisplayString;
                config false;

        description
         "SW upgrade status additional info.";
        smiv2:max-access read-only;
        smiv2:oid 1.3.6.1.4.1.1332.1.1.5.3.1.10.20;
      }
    }

    container msanSystemLogsUpload {
      smiv2:oid 1.3.6.1.4.1.1332.1.1.5.3.1.11;

      leaf msanSystemLogsUploadStart {
        type enumeration {
          enum enable {
            value 1;
          }
          enum disable {
            value 2;
          }
        }
        description
         "Control of system logs upload procedure.
          When set to enable(1) transfer of file to defined server is started.";
        smiv2:defval disable;
        smiv2:max-access read-write;
        smiv2:oid 1.3.6.1.4.1.1332.1.1.5.3.1.11.1;
      }

      leaf msanSystemLogsUploadStatus {
        type enumeration {
          enum inprogress {
            value 1;
          }
          enum successful {
            value 2;
          }
          enum failed {
            value 3;
          }
          enum notInitiated {
            value 4;
          }
        }
                config false;

        description
         "The system logs upload status info.";
        smiv2:defval notInitiated;
        smiv2:max-access read-only;
        smiv2:oid 1.3.6.1.4.1.1332.1.1.5.3.1.11.2;
      }

      leaf msanSystemLogsUploadServerIpAddressType {
        type inet-address:InetAddressType;
        description
         "Specifies the type of the system logs upload server address: ipv4[1], ipv6[2].";
        smiv2:defval ipv4;
        smiv2:max-access read-write;
        smiv2:oid 1.3.6.1.4.1.1332.1.1.5.3.1.11.3;
      }

      leaf msanSystemLogsUploadServerIpAddress {
        type inet-address:InetAddress;
        description
         "The remote system logs upload server IP address.";
        smiv2:max-access read-write;
        smiv2:oid 1.3.6.1.4.1.1332.1.1.5.3.1.11.4;
      }

      leaf msanSystemLogsUploadServerDnsName {
        type rfc1213-mib:DisplayString;
        description
         "The remote system logs upload server dns name.";
        smiv2:defval "";
        smiv2:max-access read-write;
        smiv2:oid 1.3.6.1.4.1.1332.1.1.5.3.1.11.5;
      }

      leaf msanSystemLogsUploadProtocol {
        type enumeration {
          enum tftp {
            value 1;
          }
          enum ftp {
            value 2;
          }
          enum sftp {
            value 3;
          }
        }
        description
         "The system logs upload protocol.";
        smiv2:defval tftp;
        smiv2:max-access read-write;
        smiv2:oid 1.3.6.1.4.1.1332.1.1.5.3.1.11.6;
      }

      leaf msanSystemLogsUploadProtocolPortId {
        type int32 {
          range "-1..65535";
        }
        description
         "The system logs upload protocol port number.
          If value is set to -1, standard protocol number is used.";
        smiv2:defval -1;
        smiv2:max-access read-write;
        smiv2:oid 1.3.6.1.4.1.1332.1.1.5.3.1.11.7;
      }

      leaf msanSystemLogsUploadUserName {
        type rfc1213-mib:DisplayString;
        description
         "The username used in system logs upload protocol.
          
          When sftp upgrade protocol is used, username must be set.";
        smiv2:defval "";
        smiv2:max-access read-write;
        smiv2:oid 1.3.6.1.4.1.1332.1.1.5.3.1.11.8;
      }

      leaf msanSystemLogsUploadUserPassword {
        type rfc1213-mib:DisplayString;
        description
         "The user password used in system logs upload protocol.
          
          When sftp upgrade protocol is used, username must be set.";
        smiv2:defval "";
        smiv2:max-access read-write;
        smiv2:oid 1.3.6.1.4.1.1332.1.1.5.3.1.11.9;
      }

      leaf msanSystemLogsUploadPath {
        type rfc1213-mib:DisplayString;
        description
         "The path to the system logs file location.";
        smiv2:defval "";
        smiv2:max-access read-write;
        smiv2:oid 1.3.6.1.4.1.1332.1.1.5.3.1.11.10;
      }

      leaf msanSystemLogsUploadFileName {
        type rfc1213-mib:DisplayString;
        description
         "The system logs file name";
        smiv2:defval "";
        smiv2:max-access read-write;
        smiv2:oid 1.3.6.1.4.1.1332.1.1.5.3.1.11.11;
      }
    }

    container msanSystemAutoSaveConfig {
            config false;

      smiv2:oid 1.3.6.1.4.1.1332.1.1.5.3.1.12;

      leaf msanSystemAutoSaveConfigStatus {
        type enumeration {
          enum active {
            value 1;
          }
          enum inactive {
            value 2;
          }
        }
        description
         "Description.";
        smiv2:max-access read-only;
        smiv2:oid 1.3.6.1.4.1.1332.1.1.5.3.1.12.1;
      }

      leaf msanSystemAutoSaveConfigMaxTimeout {
        type int32;
        description
         "Initial (max) number of seconds until timer for automatic saveconfig elapses.";
        smiv2:max-access read-only;
        smiv2:oid 1.3.6.1.4.1.1332.1.1.5.3.1.12.2;
      }

      leaf msanSystemAutoSaveConfigCurrTimeout {
        type int32;
        description
         "Current number of seconds until timer for automatic saveconfig elapses.";
        smiv2:max-access read-only;
        smiv2:oid 1.3.6.1.4.1.1332.1.1.5.3.1.12.3;
      }
    }

    container msanProfiles {
      smiv2:oid 1.3.6.1.4.1.1332.1.1.5.3.3;

      leaf msanProfileConfigStatus {
        type enumeration {
          enum enable {
            value 1;
          }
          enum disable {
            value 2;
          }
        }
        description
         "Profile configuration  status.";
        smiv2:defval disable;
        smiv2:max-access read-write;
        smiv2:oid 1.3.6.1.4.1.1332.1.1.5.3.3.100;
      }
    }

    container msanDhcpRaGlobal {
      smiv2:oid 1.3.6.1.4.1.1332.1.1.5.3.4.1;

      leaf msanDhcpRaMode {
        type enumeration {
          enum full {
            value 1;
          }
          enum simplified {
            value 2;
          }
        }
        description
         "Specifies if the DHCP Relay Agent mode is to be Simple or Full. Default value is Full.";
        smiv2:max-access read-write;
        smiv2:oid 1.3.6.1.4.1.1332.1.1.5.3.4.1.2;
      }

      leaf msanDhcpRaFullModeSrvIpAddr {
        type inet:ipv4-address;
        description
         "The IP address of default DHCP Server for VLANs where DHCP RA is enabled
          in full mode (parameter msanDhcpRaVlanMode).";
        smiv2:max-access read-write;
        smiv2:oid 1.3.6.1.4.1.1332.1.1.5.3.4.1.9;
      }

      leaf msanDhcpRaCircuitIdCustomFormat {
        type rfc1213-mib:DisplayString;
        description
         "DHCP Circuit Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval "";
        smiv2:max-access read-write;
        smiv2:oid 1.3.6.1.4.1.1332.1.1.5.3.4.1.11;
      }

      leaf msanDhcpRaRemoteIdCustomFormat {
        type rfc1213-mib:DisplayString;
        description
         "DHCP Remote Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval $PORT_REM_ID;
        smiv2:max-access read-write;
        smiv2:oid 1.3.6.1.4.1.1332.1.1.5.3.4.1.12;
      }
    }

    container msanDhcpRaStatGlobal {
      smiv2:oid 1.3.6.1.4.1.1332.1.1.5.3.4.4;

      leaf msanDhcpRaStatGlobalDiscover {
        type yang:counter32;
        description
         "Number of DHCP DISCOVER packets. ";
        smiv2:max-access read-only;
        smiv2:oid 1.3.6.1.4.1.1332.1.1.5.3.4.4.1;
      }

      leaf msanDhcpRaStatGlobalRequest {
        type yang:counter32;
        description
         "Number of DHCP REQUEST packets.";
        smiv2:max-access read-only;
        smiv2:oid 1.3.6.1.4.1.1332.1.1.5.3.4.4.2;
      }

      leaf msanDhcpRaStatGlobalOffer {
        type yang:counter32;
        description
         "Number of DHCP OFFER packets.";
        smiv2:max-access read-only;
        smiv2:oid 1.3.6.1.4.1.1332.1.1.5.3.4.4.3;
      }

      leaf msanDhcpRaStatGlobalACK {
        type yang:counter32;
        description
         "Number of DHCP ACKNOWLAGE (ACK) packets.";
        smiv2:max-access read-only;
        smiv2:oid 1.3.6.1.4.1.1332.1.1.5.3.4.4.4;
      }

      leaf msanDhcpRaStatGlobalNAK {
        type yang:counter32;
        description
         "Number of NOT ACKNOWLAGE (NAK) packets.";
        smiv2:max-access read-only;
        smiv2:oid 1.3.6.1.4.1.1332.1.1.5.3.4.4.5;
      }

      leaf msanDhcpRaStatGlobalDecline {
        type yang:counter32;
        description
         "Number of DHCP DECLINE packets.";
        smiv2:max-access read-only;
        smiv2:oid 1.3.6.1.4.1.1332.1.1.5.3.4.4.6;
      }

      leaf msanDhcpRaStatGlobalMaxPacketSizeExceeded {
        type yang:counter32;
        description
         "Number of DHCP packets with max. packet size exceeded. ";
        smiv2:max-access read-only;
        smiv2:oid 1.3.6.1.4.1.1332.1.1.5.3.4.4.7;
      }

      leaf msanDhcpRaStatGlobalFrameErr {
        type yang:counter32;
        description
         "Number of DHCP packets with errors in frames. ";
        smiv2:max-access read-only;
        smiv2:oid 1.3.6.1.4.1.1332.1.1.5.3.4.4.8;
      }

      leaf msanDhcpRaStatGlobalOpt82Present {
        type yang:counter32;
        description
         "Number of DHCP packets with Option 82 or giaddr present. ";
        smiv2:max-access read-only;
        smiv2:oid 1.3.6.1.4.1.1332.1.1.5.3.4.4.9;
      }

      leaf msanDhcpRaStatGlobalFrameUnsync {
        type yang:counter32;
        description
         "Number of packets with frames not synchronized with state machines.";
        smiv2:max-access read-only;
        smiv2:oid 1.3.6.1.4.1.1332.1.1.5.3.4.4.10;
      }

      leaf msanDhcpRaStatGlobalStatRelease {
        type yang:counter32;
        description
         "Number of received DHCP RELEASE packets.";
        smiv2:max-access read-only;
        smiv2:oid 1.3.6.1.4.1.1332.1.1.5.3.4.4.11;
      }

      leaf msanDhcpRaStatGlobalStatInform {
        type yang:counter32;
        description
         "Number of received DHCP INFORM packets.";
        smiv2:max-access read-only;
        smiv2:oid 1.3.6.1.4.1.1332.1.1.5.3.4.4.12;
      }
    }

    container msanDhcpv6RaGlobal {
      smiv2:oid 1.3.6.1.4.1.1332.1.1.5.3.4.100;

      leaf msanDhcpv6RaState {
        type enumeration {
          enum enable {
            value 1;
          }
          enum disable {
            value 2;
          }
        }
        description
         "DHCPv6 Relay Agent status.";
        smiv2:defval disable;
        smiv2:max-access read-write;
        smiv2:oid 1.3.6.1.4.1.1332.1.1.5.3.4.100.1;
      }

      leaf msanDhcpv6RaMode {
        type enumeration {
          enum ldra {
            value 1;
          }
        }
        description
         "DHCPv6 Relay Agent mode.
          ldra = Lightweight DHCPRv6";
        smiv2:defval ldra;
        smiv2:max-access read-write;
        smiv2:oid 1.3.6.1.4.1.1332.1.1.5.3.4.100.2;
      }

      leaf msanDhcpv6RaInterfaceIdStandard {
        type enumeration {
          enum enable {
            value 1;
          }
          enum disable {
            value 2;
          }
        }
        description
         "DHCPv6 RA Standard Interface Id type.";
        smiv2:defval enable;
        smiv2:max-access read-write;
        smiv2:oid 1.3.6.1.4.1.1332.1.1.5.3.4.100.3;
      }

      leaf msanDhcpv6RaInterfaceIdInnerVlan {
        type int32;
        description
         "Include Inner VLAN (C-VLAN) in Circuit Id when port is in DVLAN Tunneling mode (msanPortDVlanTagMode = enable).";
        smiv2:max-access read-write;
        smiv2:oid 1.3.6.1.4.1.1332.1.1.5.3.4.100.4;
      }

      leaf msanDhcpv6RaInterfaceIdCustomFormat {
        type rfc1213-mib:DisplayString;
        description
         "DHCPv6 Interface Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval "";
        smiv2:max-access read-write;
        smiv2:oid 1.3.6.1.4.1.1332.1.1.5.3.4.100.5;
      }

      leaf msanDhcpv6RaRemoteIdCustomFormat {
        type rfc1213-mib:DisplayString;
        description
         "DHCPv6  Remote Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval $PORT_REM_ID;
        smiv2:max-access read-write;
        smiv2:oid 1.3.6.1.4.1.1332.1.1.5.3.4.100.6;
      }
    }

    container msanDhcpv6RaStatistics {
      smiv2:oid 1.3.6.1.4.1.1332.1.1.5.3.4.101;

      leaf msanDhcpv6RaStatSolicit {
        type yang:counter32;
        description
         "Number of received DHCPv6 solicit packets.";
        smiv2:max-access read-only;
        smiv2:oid 1.3.6.1.4.1.1332.1.1.5.3.4.101.100;
      }

      leaf msanDhcpv6RaStatAdvertise {
        type yang:counter32;
        description
         "Number of received DHCPv6 advertise packets.";
        smiv2:max-access read-only;
        smiv2:oid 1.3.6.1.4.1.1332.1.1.5.3.4.101.101;
      }

      leaf msanDhcpv6RaStatRequest {
        type yang:counter32;
        description
         "Number of received DHCPv6 request packets.";
        smiv2:max-access read-only;
        smiv2:oid 1.3.6.1.4.1.1332.1.1.5.3.4.101.102;
      }

      leaf msanDhcpv6RaStatReply {
        type yang:counter32;
        description
         "Number of received DHCPv6 reply packets.";
        smiv2:max-access read-only;
        smiv2:oid 1.3.6.1.4.1.1332.1.1.5.3.4.101.103;
      }

      leaf msanDhcpv6RaStatRenew {
        type yang:counter32;
        description
         "Number of received DHCPv6 renew packets.";
        smiv2:max-access read-only;
        smiv2:oid 1.3.6.1.4.1.1332.1.1.5.3.4.101.104;
      }

      leaf msanDhcpv6RaStatRebind {
        type yang:counter32;
        description
         "Number of received DHCPv6 rebind packets.";
        smiv2:max-access read-only;
        smiv2:oid 1.3.6.1.4.1.1332.1.1.5.3.4.101.105;
      }

      leaf msanDhcpv6RaStatDecline {
        type yang:counter32;
        description
         "Number of received DHCPv6 decline packets.";
        smiv2:max-access read-only;
        smiv2:oid 1.3.6.1.4.1.1332.1.1.5.3.4.101.106;
      }

      leaf msanDhcpv6RaStatReconfigure {
        type yang:counter32;
        description
         "Number of received DHCPv6 reconfigure packets.";
        smiv2:max-access read-only;
        smiv2:oid 1.3.6.1.4.1.1332.1.1.5.3.4.101.107;
      }

      leaf msanDhcpv6RaStatRelease {
        type yang:counter32;
        description
         "Number of received DHCPv6 reconfigure packets.";
        smiv2:max-access read-only;
        smiv2:oid 1.3.6.1.4.1.1332.1.1.5.3.4.101.108;
      }

      leaf msanDhcpv6RaStatInformRequest {
        type yang:counter32;
        description
         "Number of received DHCPv6 inform request packets.";
        smiv2:max-access read-only;
        smiv2:oid 1.3.6.1.4.1.1332.1.1.5.3.4.101.109;
      }

      leaf msanDhcpv6RaStatRelayForward {
        type yang:counter32;
        description
         "Number of received DHCPv6 Relay Forward packets.";
        smiv2:max-access read-only;
        smiv2:oid 1.3.6.1.4.1.1332.1.1.5.3.4.101.110;
      }

      leaf msanDhcpv6RaStatRelayReply {
        type yang:counter32;
        description
         "Number of received DHCPv6 Relay Reply packets.";
        smiv2:max-access read-only;
        smiv2:oid 1.3.6.1.4.1.1332.1.1.5.3.4.101.112;
      }

      leaf msanDhcpv6RaStatOversizeError {
        type yang:counter32;
        description
         "Number of discarded packets because max packet size exceeded.";
        smiv2:max-access read-only;
        smiv2:oid 1.3.6.1.4.1.1332.1.1.5.3.4.101.200;
      }

      leaf msanDhcpv6RaStatFrameError {
        type yang:counter32;
        description
         "Number of discareded packets because errors in frame.";
        smiv2:max-access read-only;
        smiv2:oid 1.3.6.1.4.1.1332.1.1.5.3.4.101.201;
      }

      leaf msanDhcpv6RaStatFrameUnsyncError {
        type yang:counter32;
        description
         "Number of received packets with frames not synchronized with state machines.";
        smiv2:max-access read-only;
        smiv2:oid 1.3.6.1.4.1.1332.1.1.5.3.4.101.202;
      }

      leaf msanDhcpv6RaStatSysError {
        type yang:counter32;
        description
         "Number of discared packets because system error.";
        smiv2:max-access read-only;
        smiv2:oid 1.3.6.1.4.1.1332.1.1.5.3.4.101.203;
      }
    }

    container msanSntpGlobal {
      smiv2:oid 1.3.6.1.4.1.1332.1.1.5.3.5.1;

      leaf msanSntpTzOffset {
        type binary;
        description
         "Specifies the time zone offset time in format hh:mm. Allowed range is -12 to 13.";
        smiv2:max-access read-write;
        smiv2:oid 1.3.6.1.4.1.1332.1.1.5.3.5.1.1;
      }

      leaf msanSntpTzName {
        type binary {
          length "0..32";
        }
        description
         "Time Zone name.";
        smiv2:max-access read-write;
        smiv2:oid 1.3.6.1.4.1.1332.1.1.5.3.5.1.2;
      }

      leaf msanSntpTzDstOffset {
        type binary;
        description
         "Specifies the daylight saving time offset time in format hh:mm. Allowed range is -12 to 13.";
        smiv2:max-access read-write;
        smiv2:oid 1.3.6.1.4.1.1332.1.1.5.3.5.1.3;
      }

      leaf msanSntpTzDstStartMonth {
        type int32 {
          range "1..12";
        }
        description
         "Specifies the daylight saving time start month. ";
        smiv2:max-access read-write;
        smiv2:oid 1.3.6.1.4.1.1332.1.1.5.3.5.1.4;
      }

      leaf msanSntpTzDstStartWeek {
        type int32 {
          range "1..5";
        }
        description
         "Specifies the daylight saving time start week.";
        smiv2:max-access read-write;
        smiv2:oid 1.3.6.1.4.1.1332.1.1.5.3.5.1.5;
      }

      leaf msanSntpTzDstStartDayInWeek {
        type enumeration {
          enum monday {
            value 1;
          }
          enum tuesday {
            value 2;
          }
          enum wednesday {
            value 3;
          }
          enum thursday {
            value 4;
          }
          enum friday {
            value 5;
          }
          enum saturday {
            value 6;
          }
          enum sunday {
            value 7;
          }
        }
        description
         "Specifies the daylight saving time start day in week.";
        smiv2:max-access read-write;
        smiv2:oid 1.3.6.1.4.1.1332.1.1.5.3.5.1.6;
      }

      leaf msanSntpTzDstStartTime {
        type binary;
        description
         "Specifies the daylight saving time start time. Allowed range is 00:00 to 23:59.";
        smiv2:max-access read-write;
        smiv2:oid 1.3.6.1.4.1.1332.1.1.5.3.5.1.7;
      }

      leaf msanSntpTzDstEndMonth {
        type int32 {
          range "1..12";
        }
        description
         "Specifies the daylight saving time end month.";
        smiv2:max-access read-write;
        smiv2:oid 1.3.6.1.4.1.1332.1.1.5.3.5.1.8;
      }

      leaf msanSntpTzDstEndWeek {
        type int32 {
          range "1..5";
        }
        description
         "Specifies the daylight saving time end week.";
        smiv2:max-access read-write;
        smiv2:oid 1.3.6.1.4.1.1332.1.1.5.3.5.1.9;
      }

      leaf msanSntpTzDstEndDayInWeek {
        type enumeration {
          enum monday {
            value 1;
          }
          enum tuesday {
            value 2;
          }
          enum wednesday {
            value 3;
          }
          enum thursday {
            value 4;
          }
          enum friday {
            value 5;
          }
          enum saturday {
            value 6;
          }
          enum sunday {
            value 7;
          }
        }
        description
         "Specifies the daylight saving time end start day in week.";
        smiv2:max-access read-write;
        smiv2:oid 1.3.6.1.4.1.1332.1.1.5.3.5.1.10;
      }

      leaf msanSntpTzDstEndTime {
        type binary;
        description
         "Specifies the daylight saving time end time. Allowed range is 00:00 to 23:59";
        smiv2:max-access read-write;
        smiv2:oid 1.3.6.1.4.1.1332.1.1.5.3.5.1.11;
      }
    }

    container msanSnmpGlobal {
      smiv2:oid 1.3.6.1.4.1.1332.1.1.5.3.7.1;

      leaf msanSnmpTrapRecvUdpPort {
        type uint32 {
          range "0..65535";
        }
        description
         "The UDP Port where SNMP traps are to be sent.";
        smiv2:max-access read-write;
        smiv2:oid 1.3.6.1.4.1.1332.1.1.5.3.7.1.1;
      }

      leaf msanIfOperStatusChangeCnt {
        type int32;
                config false;

        description
         "Interface operational status change counter.";
        smiv2:max-access read-only;
        smiv2:oid 1.3.6.1.4.1.1332.1.1.5.3.7.1.2;
      }
    }

    container msanIgmpSnoopingGlobal {
      smiv2:oid 1.3.6.1.4.1.1332.1.1.5.3.8.1;

      leaf msanIgmpSnoopingLoggingVlanId {
        type int32 {
          range "0..4094";
        }
        description
         "VLAN Id on which IGMP snooping logging is performed. Value 0 means that logging is disabled. ";
        smiv2:max-access read-write;
        smiv2:oid 1.3.6.1.4.1.1332.1.1.5.3.8.1.3;
      }

      leaf msanIgmpSnoopingViolationAction {
        type enumeration {
          enum remove {
            value 1;
          }
          enum discard {
            value 2;
          }
        }
        description
         "Removing one of the existing (the oldest) multicast group membership, or
          discarding a new group membership request.";
        smiv2:max-access read-write;
        smiv2:oid 1.3.6.1.4.1.1332.1.1.5.3.8.1.4;
      }

      leaf msanIgmpSnoopingGroupMembershipInterval {
        type int32 {
          range "2..3600";
        }
        description
         "The amount of time in seconds that a switch will wait for a report
          from a particular group on the selected interface before deleting the
          interface from the entry.
          This value must be greater than msanIgmpSnoopingMaxResponseTime";
        smiv2:defval 260;
        smiv2:max-access read-write;
        smiv2:oid 1.3.6.1.4.1.1332.1.1.5.3.8.1.6;
      }

      leaf msanIgmpSnoopingMaxResponseTime {
        type int32 {
          range "1..3599";
        }
        description
         "The amount of time in seconds a switch will wait on a report after sending
          a query on the selected interface.
          This value must be less than msanIgmpSnoopingGroupMembershipInterval";
        smiv2:defval 2;
        smiv2:max-access read-write;
        smiv2:oid 1.3.6.1.4.1.1332.1.1.5.3.8.1.7;
      }

      leaf msanIgmpVersion {
        type enumeration {
          enum igmpAll {
            value 1;
          }
          enum igmpVersion2 {
            value 2;
          }
          enum igmpVersion3 {
            value 3;
          }
        }
        description
         "Version of processed IGMP frames.";
        smiv2:defval igmpAll;
        smiv2:max-access read-write;
        smiv2:oid 1.3.6.1.4.1.1332.1.1.5.3.8.1.8;
      }

      leaf msanIgmpClear {
        type enumeration {
          enum enable {
            value 1;
          }
          enum disable {
            value 2;
          }
        }
        description
         "Clear all IGMP snooping entries.";
        smiv2:max-access read-write;
        smiv2:oid 1.3.6.1.4.1.1332.1.1.5.3.8.1.9;
      }
    }

    container msanIgmpStatGlobal {
      smiv2:oid 1.3.6.1.4.1.1332.1.1.5.3.8.8.1;

      leaf msanIgmpStatRxV1 {
        type yang:counter32;
        description
         "Number of received IGMP v1 packets.";
        smiv2:max-access read-only;
        smiv2:oid 1.3.6.1.4.1.1332.1.1.5.3.8.8.1.1;
      }

      leaf msanIgmpStatRxV2Join {
        type yang:counter32;
        description
         "Number of received IGMP v2 join packets.";
        smiv2:max-access read-only;
        smiv2:oid 1.3.6.1.4.1.1332.1.1.5.3.8.8.1.2;
      }

      leaf msanIgmpStatRxV2Leave {
        type yang:counter32;
        description
         "Number of received IGMP v2 leave packets.";
        smiv2:max-access read-only;
        smiv2:oid 1.3.6.1.4.1.1332.1.1.5.3.8.8.1.3;
      }

      leaf msanIgmpStatRxV3Report {
        type yang:counter32;
        description
         "Number of received IGMP v3 report packets.";
        smiv2:max-access read-only;
        smiv2:oid 1.3.6.1.4.1.1332.1.1.5.3.8.8.1.4;
      }

      leaf msanIgmpStatRxQuery {
        type yang:counter32;
        description
         "Number of received IGMP query  packets.";
        smiv2:max-access read-only;
        smiv2:oid 1.3.6.1.4.1.1332.1.1.5.3.8.8.1.5;
      }

      leaf msanIgmpStatRxError {
        type yang:counter32;
        description
         "Number of received corrupted or unknown IGMP packets.";
        smiv2:max-access read-only;
        smiv2:oid 1.3.6.1.4.1.1332.1.1.5.3.8.8.1.6;
      }

      leaf msanIgmpStatRxBlockByIgmpFilter {
        type yang:counter32;
        description
         "Number of received  IGMP packets blocked by IGMP filter.";
        smiv2:max-access read-only;
        smiv2:oid 1.3.6.1.4.1.1332.1.1.5.3.8.8.1.7;
      }

      leaf msanIgmpStatRxBlockByMcastAcl {
        type yang:counter32;
        description
         "Number of received  IGMP packets blocked by Multicast ACL.";
        smiv2:max-access read-only;
        smiv2:oid 1.3.6.1.4.1.1332.1.1.5.3.8.8.1.8;
      }

      leaf msanIgmpStatRxBlockByMcastCac {
        type yang:counter32;
        description
         "Number of received  IGMP packets blocked by Multicast CAC.";
        smiv2:max-access read-only;
        smiv2:oid 1.3.6.1.4.1.1332.1.1.5.3.8.8.1.9;
      }

      leaf msanIgmpStatRxBlockByIgmpVersion {
        type yang:counter32;
        description
         "Number of received  IGMP packets blocked by IGMP Version Control.";
        smiv2:max-access read-only;
        smiv2:oid 1.3.6.1.4.1.1332.1.1.5.3.8.8.1.10;
      }
    }

    container msanPppoeIAGlobal {
      smiv2:oid 1.3.6.1.4.1.1332.1.1.5.3.11.1;

      leaf msanPppoeIAStatus {
        type enumeration {
          enum enable {
            value 1;
          }
          enum disable {
            value 2;
          }
        }
        description
         "Specifies if the PPPOE Intermadiate Agent Service is to be Enabled or Disabled.";
        smiv2:max-access read-write;
        smiv2:oid 1.3.6.1.4.1.1332.1.1.5.3.11.1.1;
      }

      leaf msanPppoeIAVsaReplyMode {
        type enumeration {
          enum keep {
            value 1;
          }
          enum remove {
            value 2;
          }
        }
        description
         "Specifies PPPOE Intermadiate Agent keep/remove option 82 in replies.";
        smiv2:max-access read-write;
        smiv2:oid 1.3.6.1.4.1.1332.1.1.5.3.11.1.2;
      }

      leaf msanPppoeIACircuitIdStatus {
        type enumeration {
          enum enable {
            value 1;
          }
          enum disable {
            value 2;
          }
        }
        description
         "Specifies the disable/enable inserting Circuit ID suboption.";
        smiv2:max-access read-write;
        smiv2:oid 1.3.6.1.4.1.1332.1.1.5.3.11.1.3;
      }

      leaf msanPppoeIARemoteIdStatus {
        type enumeration {
          enum enable {
            value 1;
          }
          enum disable {
            value 2;
          }
        }
        description
         "Specifies the disable/enable inserting Remote ID suboption.";
        smiv2:max-access read-write;
        smiv2:oid 1.3.6.1.4.1.1332.1.1.5.3.11.1.4;
      }

      leaf msanPppoeIACircuitIdInnerVlan {
        type enumeration {
          enum enable {
            value 1;
          }
          enum disable {
            value 2;
          }
        }
        description
         "Include Inner VLAN (C-VLAN) in Circuit Id when port is in DVLAN Tunneling mode (msanPortDVlanTagMode = enable).";
        smiv2:defval disable;
        smiv2:max-access read-write;
        smiv2:oid 1.3.6.1.4.1.1332.1.1.5.3.11.1.5;
      }

      leaf msanPppoeIACircuitIdCustomFormat {
        type rfc1213-mib:DisplayString;
        description
         "PPPoE Circuit Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval "";
        smiv2:max-access read-write;
        smiv2:oid 1.3.6.1.4.1.1332.1.1.5.3.11.1.6;
      }

      leaf msanPppoeIARemoteIdCustomFormat {
        type rfc1213-mib:DisplayString;
        description
         "PPPoE Remote Id Custom format definition composed of arbitrary characters and variable macros.
          
          Use '$[h][[0|s]<len>][d[<delim>]]<macro>' format to specify:
              h  HEX variable format
              0|s  left padding with zeroes or spaces
              <len> - maximum variable length
              d  use custom delimiter for MAC/IP
              <delim> - delimiting character
              <macro>  variable macro
          
          Supported macros:
          $SHELF              - A string variable representing the shelf name as configured
                                       or acquired by this device.
          $CHASSIS           - A numeric variable ranging [0..99] and representing numerical
                                        identification of shelf.
          $PANEL               - Panel indicator: 0  front panel, 1  back panel.
          $INTF_TYPE        - Interface type: eth, dsl, gpon, mng, lag, atm, etc.
          $AGENT_BOARD - Local board position (slot number) of DHCP Relay Agent.
          $PORT                 - ID of local port the DHCP packet is received on.
          $PORT_REM_ID  - Complete remoteID string is inserted, as configured per
                                        pertaining interface.
          $INTF                   - ID of local interface the DHCP packet is received on in form
                                        as used in interface configuration (e.g.: 1/2/1).
          $INTF_DSCR       - Interface description string taken exactly as configured
                                        using 'description' command.
          $PVC_INTF          - ID of PVC interface the DHCP packet is received from (ADSL only).
          $VPI                     - ID of ATM VPI the DHCP packet is received in (ADSL only).
          $VCI                     - ID of ATM VCI the DHCP packet is received in (ADSL only).
          $CLNT_MAC        - MAC address of DHCP client sending the packet.
          $AGENT_MAC      - Local DHCP Relay Agent MAC address. If this is a switching device
                                        MNG address is used. If this is a routing device MAC address
                                        of the receiving interface is used.
          $AGENT_IPV4      - Local DHCP Relay Agent IP address. Management IPv4 address
                                         is used if this is a switching device, or IPv4 address of
                                         receiving interface is used if this is a routing device.
          $VLAN                  - Outermost VLAN ID in which the DHCP packet has been received.
                                         In case of single tagged frame this is VLAN ID of the frame.
                                         In case of double (QinQ) tagged frame, this is service
                                         provider VLAN ID.
          $VLAN_NAME      - The VLAN name, as it has been configured by user,
                                         of outermost VLAN in which the DHCP packet is received.
          $CVID                   - Valid only for double (QinQ) tagged frames. Customer (inner)
                                         VLAN ID in which the DHCP packet has been received.
          $SYSNAME          - System name as configured in SNMP agent on this device.
          $LOCATION          - Location as configured in SNMP agent on this device.
          $CONTACT           - Contact as configured in SNMP agent on this device.
          $HEX                    - Arbitrary array of hexadecimal values.
                                         Format: $<arbitrary hex values>HEX";
        smiv2:defval $PORT_REM_ID;
        smiv2:max-access read-write;
        smiv2:oid 1.3.6.1.4.1.1332.1.1.5.3.11.1.7;
      }
    }

    container msanPppoeIaStatistics {
      smiv2:oid 1.3.6.1.4.1.1332.1.1.5.3.11.3;

      leaf msanPppoeIaStatPADI {
        type yang:counter32;
        description
         "Number of PADI packets.";
        smiv2:max-access read-only;
        smiv2:oid 1.3.6.1.4.1.1332.1.1.5.3.11.3.1;
      }

      leaf msanPppoeIaStatPADR {
        type yang:counter32;
        description
         "Number of PADR packets.";
        smiv2:max-access read-only;
        smiv2:oid 1.3.6.1.4.1.1332.1.1.5.3.11.3.2;
      }

      leaf msanPppoeIaStatPADO {
        type yang:counter32;
        description
         "Number of PADO packets.";
        smiv2:max-access read-only;
        smiv2:oid 1.3.6.1.4.1.1332.1.1.5.3.11.3.3;
      }

      leaf msanPppoeIaStatPADS {
        type yang:counter32;
        description
         "Number of PADS packets.";
        smiv2:max-access read-only;
        smiv2:oid 1.3.6.1.4.1.1332.1.1.5.3.11.3.4;
      }

      leaf msanPppoeIaStatPADT {
        type yang:counter32;
        description
         "Number of PADT packets.";
        smiv2:max-access read-only;
        smiv2:oid 1.3.6.1.4.1.1332.1.1.5.3.11.3.5;
      }

      leaf msanPppoeIaStatUnsutableFrames {
        type yang:counter32;
        description
         "Number of packets with unsutable frame.";
        smiv2:max-access read-only;
        smiv2:oid 1.3.6.1.4.1.1332.1.1.5.3.11.3.6;
      }

      leaf msanPppoeIaStatUnknownFrames {
        type yang:counter32;
        description
         "Number of packets with unknown frame.";
        smiv2:max-access read-only;
        smiv2:oid 1.3.6.1.4.1.1332.1.1.5.3.11.3.7;
      }

      leaf msanPppoeIaStatInvalidFrames {
        type yang:counter32;
        description
         "Number of packets with invalid frame.";
        smiv2:max-access read-only;
        smiv2:oid 1.3.6.1.4.1.1332.1.1.5.3.11.3.8;
      }
    }

    container msanForwardingDbGlobal {
      smiv2:oid 1.3.6.1.4.1.1332.1.1.5.3.13.3;

      leaf msanAddressLearningMode {
        type enumeration {
          enum macOnly {
            value 1;
          }
          enum noMacOnly {
            value 2;
          }
        }
        status deprecated;
        description
         "Specifies how source MAC addresses are associated with the interfaces on the switch. If mode is specified as nomaconly,
          source MAC addresses are learned as pairs of incoming VLAN ID and the source MAC address. If mode is specified as maconly,
          all source MAC addresses are learned in a specified VLAN, VLAN ID of the VLAN the packet was received from is not remembered.
          This mode is used for General Purpose Service Based Tagging.";
        smiv2:max-access read-write;
        smiv2:oid 1.3.6.1.4.1.1332.1.1.5.3.13.3.1;
      }

      leaf msanAddressLearningVlanId {
        type int32 {
          range "1..4094";
        }
        status deprecated;
        description
         "This is the VLAN ID which is used for learning source MAC addresses in maconly mode. All learned MAC addresses
          will be marked as received from this VLAN. VLAN with this VLAN ID is created on the switch and all physical intefaces
          are added to this VLAN. This VLAN ID cannot be used for configuring other VLANs on the switch.";
        smiv2:max-access read-write;
        smiv2:oid 1.3.6.1.4.1.1332.1.1.5.3.13.3.2;
      }

      leaf msanSwitchAddressAgingTimeout {
        type int32 {
          range "10..1000000";
        }
        description
         "The FDB entry's address aging timeout (in seconds).";
        smiv2:defval 300;
        smiv2:max-access read-write;
        smiv2:oid 1.3.6.1.4.1.1332.1.1.5.3.13.3.3;
      }
    }

    container msanDiagnosticsGlobal {
      smiv2:oid 1.3.6.1.4.1.1332.1.1.5.3.14.1;

      leaf msanDiagnosticsFanSpeedLevel {
        type int32;
        description
         "MSAN shelf fan current speed level. Higher level defines higer speed.
          Level 0 means fan is stopped. Maximum level is defined by
          parameter msanDiagnosticsMaxFanSpeedLevel";
        smiv2:max-access read-only;
        smiv2:oid 1.3.6.1.4.1.1332.1.1.5.3.14.1.1;
      }

      leaf msanDiagnosticsMaxFanSpeedLevel {
        type int32;
        description
         "MSAN shelf fan max speed level.";
        smiv2:max-access read-only;
        smiv2:oid 1.3.6.1.4.1.1332.1.1.5.3.14.1.2;
      }
    }

    container msanPppGlobal {
      smiv2:oid 1.3.6.1.4.1.1332.1.1.5.3.15.1;

      leaf msanPppLocalIpAddress {
        type inet:ipv4-address;
        description
         "Local IP address for PPP connection";
        smiv2:max-access read-write;
        smiv2:oid 1.3.6.1.4.1.1332.1.1.5.3.15.1.1;
      }

      leaf msanPppRemoteIpAddress {
        type inet:ipv4-address;
        description
         "Remote IP address for PPP connection";
        smiv2:max-access read-write;
        smiv2:oid 1.3.6.1.4.1.1332.1.1.5.3.15.1.2;
      }

      leaf msanPppAuthProtocol {
        type enumeration {
          enum none {
            value 0;
          }
          enum chap {
            value 1;
          }
          enum pap {
            value 2;
          }
        }
        description
         "PPP authentication protocol. For MPS connection use CHAP.";
        smiv2:max-access read-write;
        smiv2:oid 1.3.6.1.4.1.1332.1.1.5.3.15.1.3;
      }

      leaf msanPppEchoInterval {
        type int32;
        units seconds;
        description
         "LCP echo interval (in seconds) for session breakdown identification.";
        smiv2:max-access read-write;
        smiv2:oid 1.3.6.1.4.1.1332.1.1.5.3.15.1.4;
      }

      leaf msanPppVanJacobsonCompression {
        type enumeration {
          enum enable {
            value 1;
          }
          enum disable {
            value 2;
          }
        }
        description
         "Control of VanJacobson compression. For MPS connection it must be disabled.";
        smiv2:max-access read-write;
        smiv2:oid 1.3.6.1.4.1.1332.1.1.5.3.15.1.5;
      }

      leaf msanPppAdminState {
        type enumeration {
          enum enable {
            value 1;
          }
          enum disable {
            value 2;
          }
        }
        description
         "Global PPP connection administrative state.";
        smiv2:max-access read-write;
        smiv2:oid 1.3.6.1.4.1.1332.1.1.5.3.15.1.6;
      }
    }

    container msanAlarmPanelGlobal {
      smiv2:oid 1.3.6.1.4.1.1332.1.1.5.3.16.1;

      leaf msanAlarmPanelAudioAlarmPriority {
        type enumeration {
          enum critical {
            value 1;
          }
          enum major {
            value 2;
          }
          enum minor {
            value 3;
          }
        }
        description
         "Alarm Panel Audio Alarm Priority.";
        smiv2:max-access read-write;
        smiv2:oid 1.3.6.1.4.1.1332.1.1.5.3.16.1.1;
      }

      leaf msanAlarmPanelSerialPortType {
        type enumeration {
          enum noConnection {
            value 1;
          }
          enum mps {
            value 2;
          }
          enum alarmPanel {
            value 3;
          }
        }
        description
         "Type of equipment connected to serial port.";
        smiv2:max-access read-write;
        smiv2:oid 1.3.6.1.4.1.1332.1.1.5.3.16.1.2;
      }
    }

    container msanDslSpecificGlobal {
      smiv2:oid 1.3.6.1.4.1.1332.1.1.5.3.19.1;

      leaf msanDslSpecificSystemState {
        type enumeration {
          enum operational {
            value 4;
          }
          enum notReady {
            value 12;
          }
        }
        description
         "VDSL system operational state. For normal blade operation this value should be operational (4).
          If value differ from 4, VDSL driver is not operational.";
        smiv2:max-access read-only;
        smiv2:oid 1.3.6.1.4.1.1332.1.1.5.3.19.1.1;
      }

      leaf msanDslSpecificSystemFirmware {
        type binary;
        description
         "VDSL firmware version.";
        smiv2:max-access read-only;
        smiv2:oid 1.3.6.1.4.1.1332.1.1.5.3.19.1.2;
      }

      leaf msanDslSpecificVectoringAdminMode {
        type enumeration {
          enum enable {
            value 1;
          }
          enum disable {
            value 2;
          }
        }
        description
         "DSL vectoring admin mode.";
        smiv2:defval disable;
        smiv2:max-access read-write;
        smiv2:oid 1.3.6.1.4.1.1332.1.1.5.3.19.1.3;
      }
    }

    container msanResetWithDelayGlobal {
      smiv2:oid 1.3.6.1.4.1.1332.1.1.5.3.21.1;

      leaf msanResetDelay {
        type int32 {
          range "0..3600";
        }
        units seconds;
        description
         "Delay in seconds before reset will be performed. If set to 0, reset countdown is stopped and reset is cancelled.
          This parameter returns number of seconds before reset. If it returns 0, reset with delay was not initiated. ";
        smiv2:max-access read-write;
        smiv2:oid 1.3.6.1.4.1.1332.1.1.5.3.21.1.1;
      }
    }

    container msanMacTableGlobal {
      smiv2:oid 1.3.6.1.4.1.1332.1.1.5.3.22.1;

      leaf msanMacTableLength {
        type uint32;
        description
         "Maximum number of MAC addresses (total length of MAC table). ";
        smiv2:max-access read-only;
        smiv2:oid 1.3.6.1.4.1.1332.1.1.5.3.22.1.1;
      }

      leaf msanMacTableUsed {
        type uint32;
        description
         "Number of entries in MAC table.";
        smiv2:max-access read-only;
        smiv2:oid 1.3.6.1.4.1.1332.1.1.5.3.22.1.2;
      }
    }

    container msanAcsGlobal {
      smiv2:oid 1.3.6.1.4.1.1332.1.1.5.3.23.1;

      leaf msanAcsServerUrl {
        type binary;
        description
         "This is URL of the ACS server in form: http://<IP_or_hostname>/acs. If hostname is used, msanDnsIpAddress and msanAcsDomainName must also be set. ";
        smiv2:max-access read-write;
        smiv2:oid 1.3.6.1.4.1.1332.1.1.5.3.23.1.1;
      }

      leaf msanPrimaryDnsIpAddress {
        type inet:ipv4-address;
        description
         "This specifies the primary DNS server IP . ";
        smiv2:max-access read-write;
        smiv2:oid 1.3.6.1.4.1.1332.1.1.5.3.23.1.2;
      }

      leaf msanSecondaryDnsIpAddress {
        type inet:ipv4-address;
        description
         "This specifies the secondary DNS server IP . ";
        smiv2:max-access read-write;
        smiv2:oid 1.3.6.1.4.1.1332.1.1.5.3.23.1.3;
      }

      leaf msanAcsDomainName {
        type binary;
        description
         "Domain name. ";
        smiv2:max-access read-write;
        smiv2:oid 1.3.6.1.4.1.1332.1.1.5.3.23.1.4;
      }

      leaf msanAcsClientStatus {
        type enumeration {
          enum enable {
            value 1;
          }
          enum disable {
            value 2;
          }
        }
        description
         "ACS client administrative status.";
        smiv2:max-access read-write;
        smiv2:oid 1.3.6.1.4.1.1332.1.1.5.3.23.1.5;
      }

      leaf msanAcsBackupConf {
        type enumeration {
          enum enable {
            value 1;
          }
          enum disable {
            value 2;
          }
        }
                status obsolete;

        description
         "Back up configuration (as CLI script) to ACS server.";
        smiv2:max-access read-write;
        smiv2:oid 1.3.6.1.4.1.1332.1.1.5.3.23.1.6;
      }
    }

    container msanStpSwitchConfigGroup {
      smiv2:oid 1.3.6.1.4.1.1332.1.1.5.3.24.3;

      leaf msanStpCstBridgePriority {
        type uint32 {
          range "0..61440";
        }
        description
         "The CSTP bridge priority in instance 0. The priority is
          in the increments of 4096. The recommended default value is 32768.";
        smiv2:max-access read-write;
        smiv2:oid 1.3.6.1.4.1.1332.1.1.5.3.24.3.1;
      }
    }

    container msanAuthentication {
      smiv2:oid 1.3.6.1.4.1.1332.1.1.5.3.25;

      leaf msanAuthenticationListCreate {
        type rfc1213-mib:DisplayString {
          length "1..15";
        }
        status deprecated;
        description
         "Authentication List Create
          If set to a non empty string, creates a new Authentication List for
          configuration.";
        smiv2:max-access read-write;
        smiv2:oid 1.3.6.1.4.1.1332.1.1.5.3.25.2;
      }
    }

    container msanNetworkGlobal {
      smiv2:oid 1.3.6.1.4.1.1332.1.1.5.3.29.1;

      leaf msanNetworkIPAddress {
        type inet:ipv4-address;
        description
         "The switch's network ip address";
        smiv2:max-access read-write;
        smiv2:oid 1.3.6.1.4.1.1332.1.1.5.3.29.1.1;
      }

      leaf msanNetworkSubnetMask {
        type inet:ipv4-address;
        description
         "The switch's network subnet mask";
        smiv2:max-access read-write;
        smiv2:oid 1.3.6.1.4.1.1332.1.1.5.3.29.1.2;
      }

      leaf msanNetworkDefaultGateway {
        type inet:ipv4-address;
        description
         "The switch's network default gateway";
        smiv2:max-access read-write;
        smiv2:oid 1.3.6.1.4.1.1332.1.1.5.3.29.1.3;
      }

      leaf msanNetworkDhcpSrvIpAddr {
        type inet:ipv4-address;
                config false;
                mandatory false;
                status obsolete;


        description
         "IP address of DHCP server used by DHCP client.";
        smiv2:max-access read-only;
        smiv2:oid 1.3.6.1.4.1.1332.1.1.5.3.29.1.4;
      }

      leaf msanNetworkDhcpSrvVendorSpecific {
        type enumeration {
          enum enable {
            value 1;
          }
          enum disable {
            value 2;
          }
        }
        description
         "DHCP client uses only vendor specific DHCP servers
          (when client sends opt. 60 to server, it should return expected vendor specific value in opt. 43)";
        smiv2:max-access read-write;
        smiv2:oid 1.3.6.1.4.1.1332.1.1.5.3.29.1.5;
      }

      leaf msanNetworkDhcpClientLeaseObtained {
        type binary;
                config false;
                status obsolete;


        description
         "The date and time when DHCP lease was obtained. ";
        smiv2:max-access read-only;
        smiv2:oid 1.3.6.1.4.1.1332.1.1.5.3.29.1.6;
      }

      leaf msanNetworkDhcpClientLeaseExpires {
        type binary;
                config false;
                status obsolete;


        description
         "The date and time for which the DHCP lease is valid.";
        smiv2:max-access read-only;
        smiv2:oid 1.3.6.1.4.1.1332.1.1.5.3.29.1.7;
      }

      leaf msanNetworkDhcpClientLocalOpt82 {
        type enumeration {
          enum enable {
            value 1;
          }
          enum disable {
            value 2;
          }
        }
        description
         "DHCP client adds relay agent information option into its own outgoing frames.";
        smiv2:max-access read-write;
        smiv2:oid 1.3.6.1.4.1.1332.1.1.5.3.29.1.8;
      }
    }

    container msanUserConfigGlobal {
      smiv2:oid 1.3.6.1.4.1.1332.1.1.5.3.31.1;

      leaf msanUserConfigCheckPassword {
        type binary {
          length "0..255";
        }
        description
         "Parameter is used to check user's password. String must
          be written in next format: user_name password
          First blank space is used as delimeter between user_name and
          password.
          
          If password is ok and user has write permission,
          noError(0) code is returned.
          
          If password is ok but user has only read permission,
          noAccess(6) error code is returned.
          
          If password is not valid or user is not configured,
          inconsistentValue(12) error code is returned.";
        smiv2:max-access read-write;
        smiv2:oid 1.3.6.1.4.1.1332.1.1.5.3.31.1.1;
      }
    }

    container msanMacSgGlobal {
      smiv2:oid 1.3.6.1.4.1.1332.1.1.5.3.34.1;

      leaf msanMacSgStatus {
        type enumeration {
          enum enable {
            value 1;
          }
          enum disable {
            value 2;
          }
        }
        description
         "Administrative state of MAC Source Guard on the system.";
        smiv2:max-access read-write;
        smiv2:oid 1.3.6.1.4.1.1332.1.1.5.3.34.1.1;
      }
    }

    container msanErrorDisableGlobal {
      smiv2:oid 1.3.6.1.4.1.1332.1.1.5.3.35.1;

      leaf msanErrorDisableInterval {
        type int32;
        units minutes;
        description
         "The interval in minutes that will pass since error-disabled interface
          will be enabled. This parameter has effect only if ErrorDisable Recovery
          is enabled.";
        smiv2:max-access read-write;
        smiv2:oid 1.3.6.1.4.1.1332.1.1.5.3.35.1.1;
      }

      leaf msanErrorDisableMacSgDetectionStatus {
        type enumeration {
          enum enable {
            value 1;
          }
          enum disable {
            value 2;
          }
        }
        description
         "Administrative state of ErrorDisable Detection for MAC Source Guard cause.
          If enabled, interface will be error-disabled when MAC Source Guard violation
          is detected.";
        smiv2:max-access read-write;
        smiv2:oid 1.3.6.1.4.1.1332.1.1.5.3.35.1.2;
      }

      leaf msanErrorDisableMacSgRecoveryStatus {
        type enumeration {
          enum enable {
            value 1;
          }
          enum disable {
            value 2;
          }
        }
        description
         "Administrative state of ErrorDisable Recovery for MAC Source Guard cause.
          If enabled, interface will be automatically recovered when error-disabled
          due to MAC Source Guard violation.";
        smiv2:max-access read-write;
        smiv2:oid 1.3.6.1.4.1.1332.1.1.5.3.35.1.3;
      }
    }

    container msanEapsGlobal {
      smiv2:oid 1.3.6.1.4.1.1332.1.1.5.3.37.1;

      leaf msanEapsAdminState {
        type enumeration {
          enum enable {
            value 1;
          }
          enum disable {
            value 2;
          }
        }
        description
         "Global EAPS administrative state.";
        smiv2:defval disable;
        smiv2:max-access read-write;
        smiv2:oid 1.3.6.1.4.1.1332.1.1.5.3.37.1.1;
      }
    }

    container msanCpeGlobal {
      smiv2:oid 1.3.6.1.4.1.1332.1.1.5.3.38.1;

      leaf msanCpeReset {
        type uint32;
        units ifIndex;
        description
         "Reset CPE equipment connected to selected interface index (ifIndex).";
        smiv2:defval 0;
        smiv2:max-access read-write;
        smiv2:oid 1.3.6.1.4.1.1332.1.1.5.3.38.1.1;
      }

      leaf msanCpeSendConfig {
        type uint32;
        units ifIndex;
        description
         "Apply configuration to CPE equipment connected to
          selected interface index (ifIndex).";
        smiv2:defval 0;
        smiv2:max-access read-write;
        smiv2:oid 1.3.6.1.4.1.1332.1.1.5.3.38.1.2;
      }

      leaf msanCpeApiMajorVersion {
        type binary {
          length "0..32";
        }
        description
         "CPE API major version information.";
        smiv2:max-access read-only;
        smiv2:oid 1.3.6.1.4.1.1332.1.1.5.3.38.1.3;
      }

      leaf msanCpeApiMinorVersion {
        type binary {
          length "0..32";
        }
        description
         "CPE API minor version information.";
        smiv2:max-access read-only;
        smiv2:oid 1.3.6.1.4.1.1332.1.1.5.3.38.1.4;
      }
    }

    container msanBoardGlobal {
      smiv2:oid 1.3.6.1.4.1.1332.1.1.5.3.39.1;

      leaf msanBoardReset {
        type int32;
        description
         "Reset board in specified shelf slot ID (>0).";
        smiv2:defval 0;
        smiv2:max-access read-write;
        smiv2:oid 1.3.6.1.4.1.1332.1.1.5.3.39.1.1;
      }
    }

    container msanFtpServerGlobal {
      smiv2:oid 1.3.6.1.4.1.1332.1.1.5.3.40.1;

      leaf msanFtpServerAdminState {
        type enumeration {
          enum enable {
            value 1;
          }
          enum disable {
            value 2;
          }
        }
        description
         "FTP server administrative state.";
        smiv2:defval disable;
        smiv2:max-access read-write;
        smiv2:oid 1.3.6.1.4.1.1332.1.1.5.3.40.1.1;
      }
    }

    container msanMlinecGlobal {
      smiv2:oid 1.3.6.1.4.1.1332.1.1.5.3.50.1;

      leaf msanMlinecAdminState {
        type enumeration {
          enum enable {
            value 1;
          }
          enum disable {
            value 2;
          }
        }
        description
         "MLINEC (Multi-Link Network Connectivity) administrative state.";
        smiv2:max-access read-write;
        smiv2:oid 1.3.6.1.4.1.1332.1.1.5.3.50.1.1;
      }
    }

    container msanBridgeGlobal {
      smiv2:oid 1.3.6.1.4.1.1332.1.1.5.3.102.1;

      leaf msanBridgeMode {
        type enumeration {
          enum bridge {
            value 1;
          }
          enum ccx {
            value 2;
          }
        }
        status deprecated;
        description
         "A bridge operating mode.
          bridge(1)
          ccx(2)";
        smiv2:max-access read-write;
        smiv2:oid 1.3.6.1.4.1.1332.1.1.5.3.102.1.1;
      }

      leaf msanBridgeMacTableSize {
        type int32 {
          range "64..4095";
        }
        status deprecated;
        description
         "The maximum MAC table size";
        smiv2:max-access read-write;
        smiv2:oid 1.3.6.1.4.1.1332.1.1.5.3.102.1.2;
      }

      leaf msanBridgeRedAdminMode {
        type enumeration {
          enum enable {
            value 1;
          }
          enum disable {
            value 2;
          }
        }
        status deprecated;
        description
         "Enable or disable Random Early Discard functionality.";
        smiv2:max-access read-write;
        smiv2:oid 1.3.6.1.4.1.1332.1.1.5.3.102.1.3;
      }
    }

    container msanIPSGGlobal {
      smiv2:oid 1.3.6.1.4.1.1332.1.1.5.3.103.1;

      leaf msanIPSGAdminMode {
        type enumeration {
          enum enable {
            value 1;
          }
          enum disable {
            value 2;
          }
        }
        description
         "Enable/disable IPv4 source guard for all interfaces";
        smiv2:max-access read-write;
        smiv2:oid 1.3.6.1.4.1.1332.1.1.5.3.103.1.1;
      }

      leaf msanIPSGStoreAdminMode {
        type enumeration {
          enum enable {
            value 1;
          }
          enum disable {
            value 2;
          }
        }
        description
         "Enable/disable storing of the IP-MAC binds to the interoperation table.";
        smiv2:max-access read-write;
        smiv2:oid 1.3.6.1.4.1.1332.1.1.5.3.103.1.2;
      }

      leaf msanIPSGIpv6AdminMode {
        type enumeration {
          enum enable {
            value 1;
          }
          enum disable {
            value 2;
          }
        }
        description
         "Enable/disable IPv6 source guard for all interfaces";
        smiv2:max-access read-write;
        smiv2:oid 1.3.6.1.4.1.1332.1.1.5.3.103.1.3;
      }

      leaf msanIPSGClearDynamicBinds {
        type enumeration {
          enum disable {
            value 1;
          }
          enum clear-all {
            value 2;
          }
          enum clear-dhcpv4 {
            value 3;
          }
          enum clear-dhcpv6 {
            value 4;
          }
          enum clear-nd {
            value 5;
          }
        }
        description
         "Clear IPSG snooping tables for all ports.";
        smiv2:max-access read-write;
        smiv2:oid 1.3.6.1.4.1.1332.1.1.5.3.103.1.4;
      }
    }

    container msanVlanGlobal {
      smiv2:oid 1.3.6.1.4.1.1332.1.1.5.3.105.1;

      leaf msanDVlanTagMode {
        type enumeration {
          enum enable {
            value 1;
          }
          enum disable {
            value 2;
          }
        }
        status deprecated;
        description
         "Controls the Double Vlan Tag mode on the system.";
        smiv2:max-access read-write;
        smiv2:oid 1.3.6.1.4.1.1332.1.1.5.3.105.1.1;
      }

      leaf msanVlanRemarkAdminState {
        type enumeration {
          enum enable {
            value 1;
          }
          enum disable {
            value 2;
          }
        }
        status deprecated;
        description
         "Global VLAN Remarking administrative state.";
        smiv2:defval disable;
        smiv2:max-access read-write;
        smiv2:oid 1.3.6.1.4.1.1332.1.1.5.3.105.1.2;
      }

      leaf msanInternalVlanId {
        type int32;
        description
         "Internal Vlan ID.";
        smiv2:max-access read-write;
        smiv2:oid 1.3.6.1.4.1.1332.1.1.5.3.105.1.3;
      }
    }

    container msanEnergyMeterGlobal {
      smiv2:oid 1.3.6.1.4.1.1332.1.1.5.3.107.1;

      leaf msanEnergyMeterIpAddress {
        type inet:ipv4-address;
        description
         "Energy meter's Ip address.";
        smiv2:max-access read-write;
        smiv2:oid 1.3.6.1.4.1.1332.1.1.5.3.107.1.1;
      }

      leaf msanEnergyMeterTcpPort {
        type uint32 {
          range "0..65535";
        }
        description
         "Energy meter's Tcp port.";
        smiv2:max-access read-write;
        smiv2:oid 1.3.6.1.4.1.1332.1.1.5.3.107.1.2;
      }

      leaf msanEnergyMeterAddress {
        type uint32;
        description
         "Energy meter's address.";
        smiv2:max-access read-write;
        smiv2:oid 1.3.6.1.4.1.1332.1.1.5.3.107.1.3;
      }

      leaf msanEnergyMeterPassword {
        type uint32;
        status deprecated;
        description
         "Energy meter's password.";
        smiv2:defval 0;
        smiv2:max-access read-write;
        smiv2:oid 1.3.6.1.4.1.1332.1.1.5.3.107.1.4;
      }

      leaf msanEnergyMeterSerialNo {
        type binary {
          length "1..128";
        }
        description
         "Energy meter's serial number.";
        smiv2:max-access read-only;
        smiv2:oid 1.3.6.1.4.1.1332.1.1.5.3.107.1.5;
      }

      leaf msanEnergyMeterDateTime {
        type binary;
        description
         "Energy meter's date and time in format:
          year-month-day, hour:minutes:seconds";
        smiv2:max-access read-only;
        smiv2:oid 1.3.6.1.4.1.1332.1.1.5.3.107.1.6;
      }

      leaf msanEnergyMeterCurrTariff {
        type uint32;
        description
         "Energy meter's current active tariff.";
        smiv2:max-access read-only;
        smiv2:oid 1.3.6.1.4.1.1332.1.1.5.3.107.1.7;
      }

      leaf msanEnergyMeterCurrPower {
        type uint32;
        units "0.01 kW";
        description
         "Energy meter's current measured power.";
        smiv2:max-access read-only;
        smiv2:oid 1.3.6.1.4.1.1332.1.1.5.3.107.1.8;
      }

      leaf msanEnergyMeterCoreVersion {
        type uint32;
        description
         "Energy meter's current version number.";
        smiv2:max-access read-only;
        smiv2:oid 1.3.6.1.4.1.1332.1.1.5.3.107.1.9;
      }

      leaf msanEnergyMeterFwType {
        type uint32;
        description
         "Energy meter's current firmware type.";
        smiv2:max-access read-only;
        smiv2:oid 1.3.6.1.4.1.1332.1.1.5.3.107.1.10;
      }

      leaf msanEnergyMeterFwVersion {
        type uint32;
        status deprecated;
        description
         "Energy meter's current firmware version.";
        smiv2:max-access read-only;
        smiv2:oid 1.3.6.1.4.1.1332.1.1.5.3.107.1.11;
      }

      leaf msanEnergyMeterFwCreationDate {
        type binary;
        description
         "Energy meter's current firmware creation date in format:
          year-month-day";
        smiv2:max-access read-only;
        smiv2:oid 1.3.6.1.4.1.1332.1.1.5.3.107.1.12;
      }

      leaf msanEnergyMeterStdPassword {
        type rfc1213-mib:DisplayString {
          length "0..8";
        }
        description
         "Energy meter's password as ASCII string
          (according to used standard  IEC 61107-2001 / IEC 62056-21).";
        smiv2:max-access read-write;
        smiv2:oid 1.3.6.1.4.1.1332.1.1.5.3.107.1.13;
      }

      leaf msanEnergyMeterStdFwVersion {
        type rfc1213-mib:DisplayString;
        description
         "Energy meter's current firmware version as ASCII string
          (according to used standard  IEC 61107-2001 / IEC 62056-21).";
        smiv2:max-access read-only;
        smiv2:oid 1.3.6.1.4.1.1332.1.1.5.3.107.1.14;
      }
    }

    container msanArpInspectionGlobal {
      smiv2:oid 1.3.6.1.4.1.1332.1.1.5.3.108.1;

      leaf msanArpInspectionAdminMode {
        type enumeration {
          enum enable {
            value 1;
          }
          enum disable {
            value 2;
          }
        }
        description
         "Enable/disable global dynamic arp inspection ";
        smiv2:max-access read-write;
        smiv2:oid 1.3.6.1.4.1.1332.1.1.5.3.108.1.1;
      }
    }

    container msanIsaGlobal {
      smiv2:oid 1.3.6.1.4.1.1332.1.1.5.3.109.1;

      leaf msanIsaTalAdminMode {
        type enumeration {
          enum enable {
            value 1;
          }
          enum disable {
            value 2;
          }
        }
        description
         "ISA TAL functionality global admin mode.";
        smiv2:defval disable;
        smiv2:max-access read-write;
        smiv2:oid 1.3.6.1.4.1.1332.1.1.5.3.109.1.1;
      }

      leaf msanIsaDasServerPort {
        type uint32 {
          range "0..65535";
        }
        description
         "ISA Radius DAS (Dynamic Authorization Server) port number.";
        smiv2:defval 3799;
        smiv2:max-access read-write;
        smiv2:oid 1.3.6.1.4.1.1332.1.1.5.3.109.1.2;
      }

      leaf msanIsaDasServerSecret {
        type rfc1213-mib:DisplayString {
          length "0..16";
        }
        description
         "ISA Radius DAS  (Dynamic Authorization Server) shared secret.";
        smiv2:max-access read-write;
        smiv2:oid 1.3.6.1.4.1.1332.1.1.5.3.109.1.3;
      }

      leaf msanIsaRadiusServerRetries {
        type uint32 {
          range "1..15";
        }
        description
         "Maximum number of retransmissions of a ISA Radius request packet.";
        smiv2:defval 3;
        smiv2:max-access read-write;
        smiv2:oid 1.3.6.1.4.1.1332.1.1.5.3.109.1.4;
      }

      leaf msanIsaRadiusServerTimeout {
        type uint32 {
          range "1..30";
        }
        units seconds;
        description
         "Time out duration (in seconds) before packets are retransmitted to ISA Radius server";
        smiv2:defval 3;
        smiv2:max-access read-write;
        smiv2:oid 1.3.6.1.4.1.1332.1.1.5.3.109.1.5;
      }
    }

    container msanIsaStatistics {
      smiv2:oid 1.3.6.1.4.1.1332.1.1.5.3.109.2;

      leaf msanIsaStatLoginReq {
        type yang:counter32;
        description
         "Cumulative number of Login requests.";
        smiv2:max-access read-only;
        smiv2:oid 1.3.6.1.4.1.1332.1.1.5.3.109.2.2;
      }

      leaf msanIsaStatLoginUnsuccessfulReq {
        type yang:counter32;
        description
         "Number of unsuccessful login requests.";
        smiv2:max-access read-only;
        smiv2:oid 1.3.6.1.4.1.1332.1.1.5.3.109.2.3;
      }
    }

    container msanOnuGlobal {
      smiv2:oid 1.3.6.1.4.1.1332.1.1.5.3.111.1;

      leaf msanOnuUpgradeMethodManualStart {
        type enumeration {
          enum enable {
            value 1;
          }
          enum disable {
            value 2;
          }
        }
        description
         "Start ONU manual upgrade method according to configuration in msanOnuUpgradeTable.";
        smiv2:defval disable;
        smiv2:max-access read-write;
        smiv2:oid 1.3.6.1.4.1.1332.1.1.5.3.111.1.1;
      }

      leaf msanOnuAuthMetod {
        type enumeration {
          enum serial {
            value 1;
          }
          enum password {
            value 2;
          }
          enum serialAndPassword {
            value 3;
          }
          enum noAuthentication {
            value 4;
          }
        }
        description
         "ONU authentication method.";
        smiv2:defval serial;
        smiv2:max-access read-write;
        smiv2:oid 1.3.6.1.4.1.1332.1.1.5.3.111.1.10;
      }

      leaf msanOnuAuthAutoLearning {
        type enumeration {
          enum enable {
            value 1;
          }
          enum disable {
            value 2;
          }
        }
        description
         "ONU serial number auto learning";
        smiv2:defval enable;
        smiv2:max-access read-write;
        smiv2:oid 1.3.6.1.4.1.1332.1.1.5.3.111.1.11;
      }

      leaf msanOnuBlackListChangeCnt {
        type int32;
                config false;

        description
         "ONU Blacklist change counter.";
        smiv2:max-access read-only;
        smiv2:oid 1.3.6.1.4.1.1332.1.1.5.3.111.1.13;
      }

      leaf msanOnuIfOperStatusChangeCnt {
        type int32;
                config false;

        description
         "ONUs interface operational status change counter.";
        smiv2:max-access read-only;
        smiv2:oid 1.3.6.1.4.1.1332.1.1.5.3.111.1.14;
      }

      leaf msanOnuDataEncryption {
        type enumeration {
          enum enable {
            value 1;
          }
          enum disable {
            value 2;
          }
        }
        description
         "ONU/GEM downstream data encryption.";
        smiv2:max-access read-write;
        smiv2:oid 1.3.6.1.4.1.1332.1.1.5.3.111.1.15;
      }

      leaf msanOnuDefaultConfigFileGet {
        type rfc1213-mib:DisplayString;
        description
         "msanOnuDefaultConfigFileGet parameter is used to start transfer of  ONU default config file from external tftp or ftp server to local file.
          Next syntax must be used for tftp or ftp transfer:
          tftp://<IP>|<hostname>[:<port>]/[<path>/]<remote_file_name> [<local_file_name>]
          ftp://<usr>[:<pass>]@<IP>|<hostname>[:<port>]/[<path>/]<remote_file_name>  [<local_file_name>]";
        smiv2:defval "";
        smiv2:max-access read-write;
        smiv2:oid 1.3.6.1.4.1.1332.1.1.5.3.111.1.16;
      }
    }

container msanOltGlobal {
      smiv2:oid 1.3.6.1.4.1.1332.1.1.5.3.112.1;

      leaf msanOltBlackListRefresh {
        type enumeration {
          enum enable {
            value 1;
          }
          enum disable {
            value 2;
          }
        }
        description
         "Set this option to enable to initiate a blacklist refresh for all OLT ports.";
        smiv2:max-access read-write;
        smiv2:oid 1.3.6.1.4.1.1332.1.1.5.3.112.1.1;
      }

      leaf msanOltProtectSwitchHeartbeatRepetitionDelay {
        type int32 {
          range "100..5000";
        }
        units miliseconds;
        description
         "OLT Protection Switching Heartbeat repetition delay.";
        smiv2:max-access read-write;
        smiv2:oid 1.3.6.1.4.1.1332.1.1.5.3.112.1.2;
      }

      leaf msanOltProtectSwitchHeartbeatLossThreshold {
        type int32 {
          range "1..10";
        }
        description
         "OLT Protection Switching Heartbeat loss threshold.";
        smiv2:max-access read-write;
        smiv2:oid 1.3.6.1.4.1.1332.1.1.5.3.112.1.3;
      }
    }

    container msanTacacsServerGlobal {
      smiv2:oid 1.3.6.1.4.1.1332.1.1.5.3.113.1;

      leaf msanTacacsServerTimeout {
        type int32 {
          range "1..30";
        }
        units seconds;
        description
         "TACACS server response timeout value.";
        smiv2:defval 2;
        smiv2:max-access read-write;
        smiv2:oid 1.3.6.1.4.1.1332.1.1.5.3.113.1.1;
      }
    }

    container msanBoardTable {
      status deprecated;
      description
       "Description.";
      smiv2:oid 1.3.6.1.4.1.1332.1.1.5.1.2.1;

      list msanBoardEntry {
        key msanBoardNr;
        status deprecated;
        description
         "Description.";
        smiv2:oid 1.3.6.1.4.1.1332.1.1.5.1.2.1.1;

        leaf msanBoardNr {
          type int32 {
            range "1..1000";
          }
          status deprecated;
          description
           "Unique identification of a board.";
          smiv2:max-access not-accessible;
          smiv2:oid 1.3.6.1.4.1.1332.1.1.5.1.2.1.1.1;
        }

        leaf msanBoardParentNr {
          type int32 {
            range "1..1000";
          }
          status deprecated;
          description
           "Unique identification of a parent board.";
          smiv2:max-access read-only;
          smiv2:oid 1.3.6.1.4.1.1332.1.1.5.1.2.1.1.2;
        }

        leaf msanBoardPosition {
          type int32 {
            range "1..1000";
          }
          status deprecated;
          description
           "Position of the board on the parent board.";
          smiv2:max-access read-only;
          smiv2:oid 1.3.6.1.4.1.1332.1.1.5.1.2.1.1.3;
        }

        leaf msanBoardType {
          type binary;
          status deprecated;
          description
           "Type of physical board (e.g. IDC, SGO, SFA, ...)";
          smiv2:max-access read-only;
          smiv2:oid 1.3.6.1.4.1.1332.1.1.5.1.2.1.1.4;
        }

        leaf msanBoardId {
          type binary;
          status deprecated;
          description
           "Name (actual identification) of a board.";
          smiv2:max-access read-only;
          smiv2:oid 1.3.6.1.4.1.1332.1.1.5.1.2.1.1.5;
        }

        leaf msanBoardSerialNr {
          type binary;
          status deprecated;
          description
           "Serial number of a board.";
          smiv2:max-access read-only;
          smiv2:oid 1.3.6.1.4.1.1332.1.1.5.1.2.1.1.6;
        }

        leaf msanBoardDescription {
          type binary;
          status deprecated;
          description
           "Description of the board.";
          smiv2:max-access read-write;
          smiv2:oid 1.3.6.1.4.1.1332.1.1.5.1.2.1.1.7;
        }
      }
    }

    container msanSwComponentTable {
      description
       "Description.";
      smiv2:oid 1.3.6.1.4.1.1332.1.1.5.1.3.11;

      list msanSwComponentEntry {
        key msanSwComponentName;
                config false;

        description
         "Description.";
        smiv2:oid 1.3.6.1.4.1.1332.1.1.5.1.3.11.1;

        leaf msanSwComponentName {
          type rfc1213-mib:DisplayString;
                    config false;

          description
           "Name of software component (e.g. ES, EV, EF, EA).";
          smiv2:max-access read-only;
          smiv2:oid 1.3.6.1.4.1.1332.1.1.5.1.3.11.1.2;
        }

        leaf msanSwComponentSteerVersion {
          type rfc1213-mib:DisplayString;
                    config false;

          description
           "The unique steer code for this software component.";
          smiv2:max-access read-only;
          smiv2:oid 1.3.6.1.4.1.1332.1.1.5.1.3.11.1.3;
        }

        leaf msanSwComponentType {
                    type enumeration {
                        enum application {
                            value 1;
                        }
                        enum platform {
                            value 2;
                        }
                    }
                    config false;

          description
           "Type of SW component";
          smiv2:max-access read-only;
          smiv2:oid 1.3.6.1.4.1.1332.1.1.5.1.3.11.1.3;
        }

        leaf msanSwComponentExternalVersion {
          type rfc1213-mib:DisplayString;
                    config false;

          description
           "External code version of this software component.";
          smiv2:max-access read-only;
          smiv2:oid 1.3.6.1.4.1.1332.1.1.5.1.3.11.1.3;
        }
      }
    }

    container msanLicenseOnuTable {
            config false;

      description
       "Description.";
      smiv2:oid 1.3.6.1.4.1.1332.1.1.5.1.5.2;

      list msanLicenseOnuEntry {
        key msanLicenseOnuVendorId;
                config false;

        description
         " ";
        smiv2:oid 1.3.6.1.4.1.1332.1.1.5.1.5.2.1;

        leaf msanLicenseOnuVendorId {
          type rfc1213-mib:DisplayString;
          description
           "Licensed ONU vendor ID.";
          smiv2:max-access not-accessible;
          smiv2:oid 1.3.6.1.4.1.1332.1.1.5.1.5.2.1.1;
        }
      }
    }

container msanLicenseFileTable {
      description
       "Description.";
      smiv2:oid 1.3.6.1.4.1.1332.1.1.5.1.5.3;

      list msanLicenseFileEntry {
        key msanLicenseFileName;
        description
         "Description.";
        smiv2:oid 1.3.6.1.4.1.1332.1.1.5.1.5.3.1;

        leaf msanLicenseFileName {
          type rfc1213-mib:DisplayString;
          description
           "License file name (extension .lic)";
          smiv2:max-access not-accessible;
          smiv2:oid 1.3.6.1.4.1.1332.1.1.5.1.5.3.1.1;
        }

        leaf msanLicenseFileActivate {
          type enumeration {
            enum enable {
              value 1;
            }
            enum disable {
              value 2;
            }
          }
          description
           "Activate licence file from local disk.";
          smiv2:max-access read-write;
          smiv2:oid 1.3.6.1.4.1.1332.1.1.5.1.5.3.1.3;
        }
      }
    }

    container msanActiveLicenseTable {
      description
       "Description.";
      smiv2:oid 1.3.6.1.4.1.1332.1.1.5.1.5.4;

      list msanActiveLicenseEntry {
        key msanActiveLicenseType;
                config false;

        description
         "Description.";
        smiv2:oid 1.3.6.1.4.1.1332.1.1.5.1.5.4.1;

        leaf msanActiveLicenseType {
          type enumeration {
            enum generalLicense {
              value 1;
            }
            enum nodeLicense {
              value 2;
            }
          }
          description
           "License type.";
          smiv2:max-access not-accessible;
          smiv2:oid 1.3.6.1.4.1.1332.1.1.5.1.5.4.1.2;
        }

        leaf msanActiveLicenceFileName {
          type rfc1213-mib:DisplayString;
          description
           "License file name (extension .lic)";
          smiv2:max-access read-only;
          smiv2:oid 1.3.6.1.4.1.1332.1.1.5.1.5.4.1.3;
        }

        leaf msanActiveLicenseId {
          type rfc1213-mib:DisplayString;
          description
           "License ID.";
          smiv2:max-access read-only;
          smiv2:oid 1.3.6.1.4.1.1332.1.1.5.1.5.4.1.5;
        }

        leaf msanActiveLicenseCreationDate {
          type rfc1213-mib:DisplayString;
          description
           "Licence creation date.";
          smiv2:max-access read-only;
          smiv2:oid 1.3.6.1.4.1.1332.1.1.5.1.5.4.1.6;
        }

        leaf msanActiveLicenseExpirationDate {
          type rfc1213-mib:DisplayString;
          description
           "Licence expiration date.";
          smiv2:max-access read-only;
          smiv2:oid 1.3.6.1.4.1.1332.1.1.5.1.5.4.1.7;
        }

        leaf msanActiveLicenseCustomerId {
          type rfc1213-mib:DisplayString;
          description
           "License customer  ID.";
          smiv2:defval "";
          smiv2:max-access read-only;
          smiv2:oid 1.3.6.1.4.1.1332.1.1.5.1.5.4.1.8;
        }

        leaf msanActiveLicenseNodeId {
          type rfc1213-mib:DisplayString;
          description
           "Node ID.";
          smiv2:defval "";
          smiv2:max-access read-only;
          smiv2:oid 1.3.6.1.4.1.1332.1.1.5.1.5.4.1.9;
        }

        leaf msanActiveLicenseNodeMaxOltPorts {
          type int32;
          description
           "Maximum number of supported OLT ports.";
          smiv2:max-access read-only;
          smiv2:oid 1.3.6.1.4.1.1332.1.1.5.1.5.4.1.10;
        }
      }
    }

container msanCpuDetailTable {
            config false;

      description
       "Description.";
      smiv2:oid 1.3.6.1.4.1.1332.1.1.5.1.6.1.10;

      list msanCpuDetailEntry {
        key msanCpuDetailId;
        description
         "Description.";
        smiv2:oid 1.3.6.1.4.1.1332.1.1.5.1.6.1.10.1;

        leaf msanCpuDetailId {
          type int32;
          description
           "CPU unit ID.";
          smiv2:max-access not-accessible;
          smiv2:oid 1.3.6.1.4.1.1332.1.1.5.1.6.1.10.1.1;
        }

        leaf msanCpuDetailCurUsage {
          type int32;
          units Percent;
          description
           "Current Usage of specified CPU in the last 10 sec.";
          smiv2:max-access read-only;
          smiv2:oid 1.3.6.1.4.1.1332.1.1.5.1.6.1.10.1.2;
        }

        leaf msanCpuDetailMaxUsage {
          type int32;
          units Percent;
          description
           "Maximum Usage of specified CPU.";
          smiv2:max-access read-only;
          smiv2:oid 1.3.6.1.4.1.1332.1.1.5.1.6.1.10.1.3;
        }

        leaf msanCpuDetailMinUsage {
          type int32;
          units Percent;
          description
           "Minimum Usage of specified CPU.";
          smiv2:max-access read-only;
          smiv2:oid 1.3.6.1.4.1.1332.1.1.5.1.6.1.10.1.4;
        }

        leaf msanCpuDetailAvgUsage {
          type int32;
          units Percent;
          description
           "Average Usage of specified CPU.";
          smiv2:max-access read-only;
          smiv2:oid 1.3.6.1.4.1.1332.1.1.5.1.6.1.10.1.5;
        }
      }
    }

    container msanDiskTable {
      description
       "Description.";
      smiv2:oid 1.3.6.1.4.1.1332.1.1.5.1.6.2.1;

      list msanDiskEntry {
        key msanDiskType;
        description
         "Description.";
        smiv2:oid 1.3.6.1.4.1.1332.1.1.5.1.6.2.1.1;

        leaf msanDiskType {
          type enumeration {
            enum activeDisk {
              value 1;
            }
            enum backupDisk {
              value 2;
            }
            enum logDisk {
              value 3;
            }
          }
          description
           "Disk type.";
          smiv2:max-access not-accessible;
          smiv2:oid 1.3.6.1.4.1.1332.1.1.5.1.6.2.1.1.1;
        }

        leaf msanDiskTotalSpace {
          type uint32;
          units kB;
          description
           "Total disk space of selected type.";
          smiv2:max-access read-only;
          smiv2:oid 1.3.6.1.4.1.1332.1.1.5.1.6.2.1.1.2;
        }

        leaf msanDiskFreeSpace {
          type uint32;
          units kB;
          description
           "Free disk space of selected type.";
          smiv2:max-access read-only;
          smiv2:oid 1.3.6.1.4.1.1332.1.1.5.1.6.2.1.1.3;
        }

        leaf msanDiskUsedSpace {
          type uint32;
          units kB;
          description
           "Used disk space of selected type.";
          smiv2:max-access read-only;
          smiv2:oid 1.3.6.1.4.1.1332.1.1.5.1.6.2.1.1.4;
        }
      }
    }

    container msanCliScriptTable {
      description
       "Description.";
      smiv2:oid 1.3.6.1.4.1.1332.1.1.5.3.1.6;

      list msanCliScriptEntry {
        key msanCliScriptName;
        description
         "Description.";
        smiv2:oid 1.3.6.1.4.1.1332.1.1.5.3.1.6.1;

        leaf msanCliScriptName {
          type binary {
            length "1..32";
          }
          description
           "CLI script name";
          smiv2:max-access not-accessible;
          smiv2:oid 1.3.6.1.4.1.1332.1.1.5.3.1.6.1.1;
        }

        leaf msanCliScriptApply {
          type enumeration {
            enum enable {
              value 1;
            }
            enum disable {
              value 2;
            }
          }
          description
           "When set to enable(1) selected selected CLI script is applied.";
          smiv2:max-access read-write;
          smiv2:oid 1.3.6.1.4.1.1332.1.1.5.3.1.6.1.2;
        }

        leaf msanCliScriptApplyStatus {
          type enumeration {
            enum notInitiated {
              value 1;
            }
            enum inProcess {
              value 2;
            }
          }
          description
           "Status of CLI script apply request";
          smiv2:max-access read-only;
          smiv2:oid 1.3.6.1.4.1.1332.1.1.5.3.1.6.1.3;
        }

        leaf msanCliScriptRowStatus {
          type snmpv2-tc:RowStatus;
          description
           "The row status object controls the creation/deletion of rows in this table.
            Its semantics are the same as those for the RowStatus textual convention specified for SNMPv2.
            Setting this object to destroy(6) will remove this entry.
            Read values: active(1).
            Other values are currently not supported.";
          smiv2:max-access read-write;
          smiv2:oid 1.3.6.1.4.1.1332.1.1.5.3.1.6.1.4;
        }
      }
    }

    container msanSwBootPackageTable {
      description
       "Description.";
      smiv2:oid 1.3.6.1.4.1.1332.1.1.5.3.1.9;

      list msanSwBootPackageEntry {
        key msanSwBootPackageName;
        description
         "Description.";
        smiv2:oid 1.3.6.1.4.1.1332.1.1.5.3.1.9.1;

        leaf msanSwBootPackageName {
          type rfc1213-mib:DisplayString;
          description
           "SW package name on local disk.";
          smiv2:max-access read-only;
          smiv2:oid 1.3.6.1.4.1.1332.1.1.5.3.1.9.1.1;
        }

        leaf msanSwBootPackageStatus {
          type enumeration {
            enum currentActive {
              value 1;
            }
            enum nextActive {
              value 2;
            }
            enum backup {
              value 3;
            }
            enum none {
              value 4;
            }
          }
          description
           "SW package status.
            You can set only nextActive(2) value. Other values are read-only.";
          smiv2:max-access read-write;
          smiv2:oid 1.3.6.1.4.1.1332.1.1.5.3.1.9.1.2;
        }
      }
    }

    container msanVDSLProfileTable {
      description
       "Description.";
      smiv2:oid 1.3.6.1.4.1.1332.1.1.5.3.3.1;

      list msanVDSLProfileEntry {
        key vdslLineConfProfileName;
        description
         "Description.";
        smiv2:oid 1.3.6.1.4.1.1332.1.1.5.3.3.1.1;

        leaf vdslLineConfProfileName {
          type leafref {
            path "/vdsl-line:VDSL-LINE-MIB/vdsl-line:vdslLineConfProfileTable/vdsl-line:vdslLineConfProfileEntry/vdsl-line:vdslLineConfProfileName";
          }
        }

        leaf msanVDSLProfileType {
          type enumeration {
            enum other {
              value 1;
            }
            enum default {
              value 2;
            }
            enum local {
              value 3;
            }
            enum global {
              value 4;
            }
          }
          description
           "Profile type:
            - other ~ none of the following
            - defaut ~ default profile
            - local ~ local configured profile type
            - global ~ global configured profile type";
          smiv2:max-access read-write;
          smiv2:oid 1.3.6.1.4.1.1332.1.1.5.3.3.1.1.1;
        }

        leaf msanVDSL2LineProfile {
          type enumeration {
            enum vdsl2profile8c {
              value 1;
            }
            enum vdsl2profile8d {
              value 2;
            }
            enum vdsl2profile12a {
              value 3;
            }
            enum vdsl2profile12b {
              value 4;
            }
            enum vdsl2profile17a {
              value 5;
            }
          }
          description
           "VDSL2 profile";
          smiv2:max-access read-write;
          smiv2:oid 1.3.6.1.4.1.1332.1.1.5.3.3.1.1.2;
        }
      }
    }

    container msanServiceProfileTable {
      description
       "Service Profile table ";
      smiv2:oid 1.3.6.1.4.1.1332.1.1.5.3.3.2.1;

      list msanServiceProfileEntry {
        key msanServiceProfileName;
        description
         "Service Profile table entry.";
        smiv2:oid 1.3.6.1.4.1.1332.1.1.5.3.3.2.1.1;

        leaf msanServiceProfileName {
          type rfc1213-mib:DisplayString {
            length "1..64";
          }
          description
           "Name for service profile.";
          smiv2:max-access not-accessible;
          smiv2:oid 1.3.6.1.4.1.1332.1.1.5.3.3.2.1.1.1;
        }

        leaf msanServiceProfileServiceFlowProfileName {
          type rfc1213-mib:DisplayString;
          description
           "Index of used service flow profile (this profile must be set before), which indicates
            row in msanServiceFlowProfileTable.
            Empty string indicates that parameter has not been defined.";
          smiv2:max-access read-write;
          smiv2:oid 1.3.6.1.4.1.1332.1.1.5.3.3.2.1.1.4;
        }

        leaf msanServiceProfileMulticastProfileName {
          type rfc1213-mib:DisplayString;
          description
           "Index of used multicast profile (this profile must be set before), which indicates
            row in msanMulticastProfileTable.
            Empty string indicates that parameter has not been defined.";
          smiv2:max-access read-write;
          smiv2:oid 1.3.6.1.4.1.1332.1.1.5.3.3.2.1.1.5;
        }

        leaf msanServiceProfileVlanProfileName {
          type rfc1213-mib:DisplayString;
          description
           "Index of used vlan profile (this profile must be set before), which indicates
            row in msanVlanProfileTable.
            Empty string indicates that parameter has not been defined.";
          smiv2:max-access read-write;
          smiv2:oid 1.3.6.1.4.1.1332.1.1.5.3.3.2.1.1.6;
        }

        leaf msanServiceProfileL2cpProfileName {
          type rfc1213-mib:DisplayString;
          description
           "Index of used L2CP profile (this profile must be set before), which indicates
            row in msanL2cpProfileTable.
            Empty string indicates that parameter has not been defined.";
          smiv2:max-access read-write;
          smiv2:oid 1.3.6.1.4.1.1332.1.1.5.3.3.2.1.1.7;
        }

        leaf msanServiceProfileSecurityProfileName {
          type rfc1213-mib:DisplayString;
          description
           "Index of used security profile (this profile must be set before), which indicates
            row in msanSecurityProfileTable.
            Empty string indicates that parameter has not been defined.";
          smiv2:max-access read-write;
          smiv2:oid 1.3.6.1.4.1.1332.1.1.5.3.3.2.1.1.8;
        }

        leaf msanServiceProfileAtmVpi {
          type int32 {
            range "-1..255";
          }
          description
           "Virtual Path Identifier.
            A value of -1 indicates that parameter has not been defined.";
          smiv2:defval -1;
          smiv2:max-access read-write;
          smiv2:oid 1.3.6.1.4.1.1332.1.1.5.3.3.2.1.1.9;
        }

        leaf msanServiceProfileAtmVci {
          type int32 {
            range "-1|32..65535";
          }
          description
           "Virtual Channel Identifier.
            A value of -1 indicates that parameter has not been defined.";
          smiv2:defval -1;
          smiv2:max-access read-write;
          smiv2:oid 1.3.6.1.4.1.1332.1.1.5.3.3.2.1.1.10;
        }

        leaf msanServiceProfileDhcpRa {
          type enumeration {
            enum disable {
              value 0;
            }
            enum allowClients {
              value 1;
            }
            enum allowServers {
              value 2;
            }
            enum allowAll {
              value 3;
            }
          }
          description
           "Dynamic Host Configuration Protocol Relay Agent.
            DHCP RA and PPPoE IA can not be included simultaneously.";
          smiv2:defval disable;
          smiv2:max-access read-write;
          smiv2:oid 1.3.6.1.4.1.1332.1.1.5.3.3.2.1.1.11;
        }

        leaf msanServiceProfileDhcpRaTrustClients {
          type enumeration {
            enum notTrust {
              value 0;
            }
            enum trust {
              value 1;
            }
          }
          description
           "DHCP RA Trust Clients.
            Effective only if DHCP-RA is in either allow-all or allow-client mode.";
          smiv2:defval notTrust;
          smiv2:max-access read-write;
          smiv2:oid 1.3.6.1.4.1.1332.1.1.5.3.3.2.1.1.12;
        }

        leaf msanServiceProfileDhcpRaOpt82UnicastExtension {
          type enumeration {
            enum notUsed {
              value 0;
            }
            enum used {
              value 1;
            }
          }
          description
           "DHCP RA option82 unicast extension.
            Effective only if DHCP-RA is in either allow-all or allow-client mode.";
          smiv2:defval notUsed;
          smiv2:max-access read-write;
          smiv2:oid 1.3.6.1.4.1.1332.1.1.5.3.3.2.1.1.13;
        }

        leaf msanServiceProfileDhcpRaOpt82Insert {
          type enumeration {
            enum notInsert {
              value 0;
            }
            enum insert {
              value 1;
            }
          }
          description
           "DHCP Relay Agent Insert Option 82.
            Effective only if DHCP-RA is in either allow-all or allow-client mode.";
          smiv2:defval notInsert;
          smiv2:max-access read-write;
          smiv2:oid 1.3.6.1.4.1.1332.1.1.5.3.3.2.1.1.14;
        }

        leaf msanServiceProfileDhcpRaRemoteId {
          type binary {
            length "0..63";
          }
          status deprecated;
          description
           "DHCP Relay Agent Remote Identification.
            Effective only if DHCP-RA is in either allow-all or allow-client mode.";
          smiv2:defval "";
          smiv2:max-access read-write;
          smiv2:oid 1.3.6.1.4.1.1332.1.1.5.3.3.2.1.1.15;
        }

        leaf msanServiceProfileDhcpRaRateLimit {
          type uint32 {
            range "0..1000";
          }
          description
           "Max rate for DHCP Relay Agent.";
          smiv2:defval 5;
          smiv2:max-access read-write;
          smiv2:oid 1.3.6.1.4.1.1332.1.1.5.3.3.2.1.1.16;
        }

        leaf msanServiceProfilePppoeIA {
          type enumeration {
            enum disable {
              value 0;
            }
            enum enable {
              value 1;
            }
          }
          description
           "Point-to-Point Protocol over Ethernet Intermediate Agent.
            DHCP RA and PPPoE IA can not be included simultaneously.";
          smiv2:defval disable;
          smiv2:max-access read-write;
          smiv2:oid 1.3.6.1.4.1.1332.1.1.5.3.3.2.1.1.17;
        }

        leaf msanServiceProfilePppoeIARateLimit {
          type uint32 {
            range "0..1000";
          }
          description
           "Max rate for PPPoE IA.";
          smiv2:defval 5;
          smiv2:max-access read-write;
          smiv2:oid 1.3.6.1.4.1.1332.1.1.5.3.3.2.1.1.18;
        }

        leaf msanServiceProfileDhcpRaInterfaceIdStandard {
          type enumeration {
            enum enable {
              value 1;
            }
            enum disable {
              value 2;
            }
          }
          status deprecated;
          description
           "DHCP RA Standard Interface Id (Circuit Id) syntax mode.";
          smiv2:defval disable;
          smiv2:max-access read-write;
          smiv2:oid 1.3.6.1.4.1.1332.1.1.5.3.3.2.1.1.21;
        }

        leaf msanServiceProfileDhcpv6Ra {
          type enumeration {
            enum disable {
              value 0;
            }
            enum allowClients {
              value 1;
            }
          }
          description
           "State of DHCPv6 Relay Agent on the port.";
          smiv2:defval 144242104;
          smiv2:max-access read-write;
          smiv2:oid 1.3.6.1.4.1.1332.1.1.5.3.3.2.1.1.22;
        }

        leaf msanServiceProfileDhcpv6RaTrustClients {
          type enumeration {
            enum notTrust {
              value 0;
            }
            enum trust {
              value 1;
            }
          }
          description
           "DHCPv6 Relay Agent Trust Clients.
            Effective only if DHCPv6-RA is in allow-client mode.";
          smiv2:defval notTrust;
          smiv2:max-access read-write;
          smiv2:oid 1.3.6.1.4.1.1332.1.1.5.3.3.2.1.1.23;
        }

        leaf msanServiceProfileDhcpv6RaInterfaceIdStandard {
          type enumeration {
            enum enable {
              value 1;
            }
            enum disable {
              value 2;
            }
          }
          status deprecated;
          description
           "DHCPv6 RA Standard Interface Id syntax mode.";
          smiv2:defval enable;
          smiv2:max-access read-write;
          smiv2:oid 1.3.6.1.4.1.1332.1.1.5.3.3.2.1.1.24;
        }

        leaf msanServiceProfileDhcpv6RaRemoteId {
          type binary;
          status deprecated;
          description
           "DHCPv6 Remote Id value.";
          smiv2:defval "";
          smiv2:max-access read-write;
          smiv2:oid 1.3.6.1.4.1.1332.1.1.5.3.3.2.1.1.25;
        }

        leaf msanServiceProfileDhcpv6RaRemoteIdEnterpriseNum {
          type int32 {
            range "1..999999";
          }
          description
           "DHCPv6 Remote Id enterprise number.";
          smiv2:defval 1332;
          smiv2:max-access read-write;
          smiv2:oid 1.3.6.1.4.1.1332.1.1.5.3.3.2.1.1.26;
        }

        leaf msanServiceProfileDhcpRaCircuitIdType {
          type enumeration {
            enum iskratel {
              value 1;
            }
            enum standard {
              value 2;
            }
            enum atm {
              value 3;
            }
            enum custom {
              value 4;
            }
          }
          description
           "DHCP Circuit Id syntax mode.";
          smiv2:defval iskratel;
          smiv2:max-access read-write;
          smiv2:oid 1.3.6.1.4.1.1332.1.1.5.3.3.2.1.1.27;
        }

        leaf msanServiceProfilePPPoeIACircuitIdType {
          type enumeration {
            enum iskratel {
              value 1;
            }
            enum atm {
              value 3;
            }
            enum custom {
              value 4;
            }
          }
          description
           "PPPoE Circuit Id syntax mode per port.";
          smiv2:max-access read-write;
          smiv2:oid 1.3.6.1.4.1.1332.1.1.5.3.3.2.1.1.28;
        }

        leaf msanServiceProfileDhcpRaCircuitIdCustomFormat {
          type rfc1213-mib:DisplayString;
          description
           "DHCP Circuit Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.29;
        }

        leaf msanServiceProfileDhcpRaRemoteIdCustomFormat {
          type rfc1213-mib:DisplayString;
          description
           "DHCP Remote Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.30;
        }

        leaf msanServiceProfilePPPoeIACircuitIdCustomFormat {
          type rfc1213-mib:DisplayString;
          description
           "PPPoE Circuit Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.31;
        }

        leaf msanServiceProfilePPPoeIARemoteIdCustomFormat {
          type rfc1213-mib:DisplayString;
          description
           "PPPoE Remote Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.32;
        }

        leaf msanServiceProfileDhcpv6RaInterfaceIdType {
          type enumeration {
            enum iskratel {
              value 1;
            }
            enum standard {
              value 2;
            }
            enum custom {
              value 3;
            }
          }
          description
           "DHCPv6  Interface Id syntax mode.";
          smiv2:defval standard;
          smiv2:max-access read-write;
          smiv2:oid 1.3.6.1.4.1.1332.1.1.5.3.3.2.1.1.33;
        }

        leaf msanServiceProfileDhcpv6RaInterfaceIdCustomFormat {
          type rfc1213-mib:DisplayString;
          description
           "DHCPv6 Interface Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.34;
        }

        leaf msanServiceProfileDhcpv6RaRemoteIdCustomFormat {
          type rfc1213-mib:DisplayString;
          description
           "DHCPv6 Remote Id Custom format definition composed of arbitrary characters and variable macros.
            
            Use '$[h][[0|s]<len>][d[<delim>]]<macro>' format to specify:
                h  HEX variable format
                0|s  left padding with zeroes or spaces
                <len> - maximum variable length
                d  use custom delimiter for MAC/IP
                <delim> - delimiting character
                <macro>  variable macro
            
            Supported macros:
            $SHELF              - A string variable representing the shelf name as configured
                                         or acquired by this device.
            $CHASSIS           - A numeric variable ranging [0..99] and representing numerical
                                          identification of shelf.
            $PANEL               - Panel indicator: 0  front panel, 1  back panel.
            $INTF_TYPE        - Interface type: eth, dsl, gpon, mng, lag, atm, etc.
            $AGENT_BOARD - Local board position (slot number) of DHCP Relay Agent.
            $PORT                 - ID of local port the DHCP packet is received on.
            $PORT_REM_ID  - Complete remoteID string is inserted, as configured per
                                          pertaining interface.
            $INTF                   - ID of local interface the DHCP packet is received on in form
                                          as used in interface configuration (e.g.: 1/2/1).
            $INTF_DSCR       - Interface description string taken exactly as configured
                                          using 'description' command.
            $PVC_INTF          - ID of PVC interface the DHCP packet is received from (ADSL only).
            $VPI                     - ID of ATM VPI the DHCP packet is received in (ADSL only).
            $VCI                     - ID of ATM VCI the DHCP packet is received in (ADSL only).
            $CLNT_MAC        - MAC address of DHCP client sending the packet.
            $AGENT_MAC      - Local DHCP Relay Agent MAC address. If this is a switching device
                                          MNG address is used. If this is a routing device MAC address
                                          of the receiving interface is used.
            $AGENT_IPV4      - Local DHCP Relay Agent IP address. Management IPv4 address
                                           is used if this is a switching device, or IPv4 address of
                                           receiving interface is used if this is a routing device.
            $VLAN                  - Outermost VLAN ID in which the DHCP packet has been received.
                                           In case of single tagged frame this is VLAN ID of the frame.
                                           In case of double (QinQ) tagged frame, this is service
                                           provider VLAN ID.
            $VLAN_NAME      - The VLAN name, as it has been configured by user,
                                           of outermost VLAN in which the DHCP packet is received.
            $CVID                   - Valid only for double (QinQ) tagged frames. Customer (inner)
                                           VLAN ID in which the DHCP packet has been received.
            $SYSNAME          - System name as configured in SNMP agent on this device.
            $LOCATION          - Location as configured in SNMP agent on this device.
            $CONTACT           - Contact as configured in SNMP agent on this device.
            $HEX                    - Arbitrary array of hexadecimal values.
                                           Format: $<arbitrary hex values>HEX";
          smiv2:defval "";
          smiv2:max-access read-write;
          smiv2:oid 1.3.6.1.4.1.1332.1.1.5.3.3.2.1.1.35;
        }

        leaf msanServiceProfileOnuFlowProfileName {
          type rfc1213-mib:DisplayString;
          description
           "Index of used ONU Flow profile (this profile must be set before), which indicates
            row in msanOnuFlowProfileTable.
            Empty string indicates that parameter has not been defined.";
          smiv2:max-access read-write;
          smiv2:oid 1.3.6.1.4.1.1332.1.1.5.3.3.2.1.1.50;
        }

        leaf msanServiceProfileOnuVlanProfileName {
          type rfc1213-mib:DisplayString;
          description
           "Index of used ONU Vlan profile (this profile must be set before), which indicates
            row in msanOnuVlanProfileTable.
            Empty string indicates that parameter has not been defined.";
          smiv2:max-access read-write;
          smiv2:oid 1.3.6.1.4.1.1332.1.1.5.3.3.2.1.1.51;
        }

        leaf msanServiceProfileOnuMulticastProfileName {
          type rfc1213-mib:DisplayString;
          description
           "Index of used ONU Multicast profile (this profile must be set before), which indicates
            row in msanOnuMulticastProfileTable.
            Empty string indicates that parameter has not been defined.";
          smiv2:max-access read-write;
          smiv2:oid 1.3.6.1.4.1.1332.1.1.5.3.3.2.1.1.52;
        }

        leaf msanServiceProfileOnuTcontProfileName {
          type rfc1213-mib:DisplayString;
          description
           "Index of used ONU T-CONT profile (this profile must be set before), which indicates
            row in msanOnuTcontProfileTable.
            Empty string indicates that parameter has not been defined.";
          smiv2:max-access read-write;
          smiv2:oid 1.3.6.1.4.1.1332.1.1.5.3.3.2.1.1.53;
        }

        leaf msanServiceProfileOnuVirtGemPortId {
          type int32 {
            range "1..32";
          }
          description
           "Virtual GEM Port ID.";
          smiv2:defval 1;
          smiv2:max-access read-write;
          smiv2:oid 1.3.6.1.4.1.1332.1.1.5.3.3.2.1.1.54;
        }

        leaf msanServiceProfileOnuTpType {
          type enumeration {
            enum veip {
              value 1;
            }
            enum ipHost {
              value 2;
            }
            enum ethernetUni {
              value 3;
            }
          }
          description
           "ONU termination point type.";
          smiv2:max-access read-write;
          smiv2:oid 1.3.6.1.4.1.1332.1.1.5.3.3.2.1.1.55;
        }

        leaf msanServiceProfileOnuTpUniBitMap {
          type binary {
            length "0..2";
          }
          description
           "ONU Ethernet UNI ports bitmap (max 16 ports). This parameter can be set only
            when msanServiceProfileOnuTpType has value ethernetUni(3).";
          smiv2:max-access read-write;
          smiv2:oid 1.3.6.1.4.1.1332.1.1.5.3.3.2.1.1.56;
        }
                leaf msanServiceProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanServicePortProfileTable {
      description
       "A connection between service profiles and device ports";
      smiv2:oid 1.3.6.1.4.1.1332.1.1.5.3.3.2.2;

      list msanServicePortProfileEntry {
        key "ifName msanServiceProfileName";
        description
         "Service Profile Port table entry.";
        smiv2:oid 1.3.6.1.4.1.1332.1.1.5.3.3.2.2.1;

        leaf ifName {
          type if:interface-ref;
          description 
           "A reference to the name of a configured network layer
            interface.";
        }

        leaf msanServiceProfileName {
          type leafref {
            path "/iskratel-msan:ISKRATEL-MSAN-MIB/iskratel-msan:msanServiceProfileTable/iskratel-msan:msanServiceProfileEntry/iskratel-msan:msanServiceProfileName";
          }
        }
      }
    }

    container msanServiceFlowProfileTable {
      description
       "Service Flow Profile table ";
      smiv2:oid 1.3.6.1.4.1.1332.1.1.5.3.3.3.1;

      list msanServiceFlowProfileEntry {
        key msanServiceFlowProfileName;
        description
         "Service Flow Profile table entry.";
        smiv2:oid 1.3.6.1.4.1.1332.1.1.5.3.3.3.1.1;

        leaf msanServiceFlowProfileName {
          type rfc1213-mib:DisplayString {
            length "1..32";
          }
          description
           "Service Flow Profile Name.";
          smiv2:max-access not-accessible;
          smiv2:oid 1.3.6.1.4.1.1332.1.1.5.3.3.3.1.1.1;
        }

        leaf msanServiceFlowProfileMatchUsAny {
          type enumeration {
            enum enable {
              value 1;
            }
            enum disable {
              value 2;
            }
          }
          description
           "Match every upstream packet frame.";
          smiv2:defval disable;
          smiv2:max-access read-write;
          smiv2:oid 1.3.6.1.4.1.1332.1.1.5.3.3.3.1.1.4;
        }

        leaf msanServiceFlowProfileMatchUsMacDestAddr {
          type yang:mac-address;
          description
           "Match upstream packet frame with specified destination MAC address.
            Empty string indicates that parameter has not been defined";
          smiv2:defval "";
          smiv2:max-access read-write;
          smiv2:oid 1.3.6.1.4.1.1332.1.1.5.3.3.3.1.1.5;
        }

        leaf msanServiceFlowProfileMatchUsMacDestMask {
          type yang:mac-address;
          description
           "This mask value identifies the portion of msanServiceFlowProfileMatchUsMacDestAddr
            that is compared with upstream packet.
            Empty string indicates that parameter has not been defined";
          smiv2:defval "";
          smiv2:max-access read-write;
          smiv2:oid 1.3.6.1.4.1.1332.1.1.5.3.3.3.1.1.6;
        }

        leaf msanServiceFlowProfileMatchUsMacSrcAddr {
          type yang:mac-address;
          description
           "Match upstream packet frame with specified source MAC address.
            Empty string indicates that parameter has not been defined";
          smiv2:defval "";
          smiv2:max-access read-write;
          smiv2:oid 1.3.6.1.4.1.1332.1.1.5.3.3.3.1.1.7;
        }

        leaf msanServiceFlowProfileMatchUsMacSrcMask {
          type yang:mac-address;
          description
           "This mask value identifies the portion of msanServiceFlowProfileMatchUsMacSrcAddr
            that is compared with upstream packet.
            Empty string indicates that parameter has not been defined";
          smiv2:defval "";
          smiv2:max-access read-write;
          smiv2:oid 1.3.6.1.4.1.1332.1.1.5.3.3.3.1.1.8;
        }

        leaf msanServiceFlowProfileMatchUsCPcp {
          type int32;
          description
           "Match upstream packet frame with specified Customer PCP (Priority Code Point) -
            PCP is also known as class of service (CoS) bits.
            A value of -1 indicates that parameter has not been defined.";
          smiv2:defval -1;
          smiv2:max-access read-write;
          smiv2:oid 1.3.6.1.4.1.1332.1.1.5.3.3.3.1.1.9;
        }

        leaf msanServiceFlowProfileMatchUsSPcp {
          type int32;
          description
           "Match upstream packet frame with specified Service PCP  (Priority Code Point).
            PCP is also known as class of service (CoS) bits.
            A value of -1 indicates that parameter has not been defined.";
          smiv2:defval -1;
          smiv2:max-access read-write;
          smiv2:oid 1.3.6.1.4.1.1332.1.1.5.3.3.3.1.1.10;
        }

        leaf msanServiceFlowProfileMatchUsVlanProfile {
          type enumeration {
            enum enable {
              value 1;
            }
            enum disable {
              value 2;
            }
          }
          description
           "Match upstream packet frame with VLAN Id values from VLAN Service Profile (msanVlanProfileTable).";
          smiv2:defval disable;
          smiv2:max-access read-write;
          smiv2:oid 1.3.6.1.4.1.1332.1.1.5.3.3.3.1.1.11;
        }

        leaf msanServiceFlowProfileMatchUsCVlanIdRange {
          type binary {
            length "0..512";
          }
          description
           "Match upstream packet frame with specified list (bitmask) of Customer VLAN Id.
            An empty string indicates that parameter has not been defined.";
          smiv2:defval "";
          smiv2:max-access read-write;
          smiv2:oid 1.3.6.1.4.1.1332.1.1.5.3.3.3.1.1.12;
        }

        leaf msanServiceFlowProfileMatchUsSVlanIdRange {
          type binary {
            length "0..512";
          }
          description
           "Match upstream packet frame with specified list (bitmask) of Service VLAN Id.
            An empty string indicates that parameter has not been defined.";
          smiv2:defval "";
          smiv2:max-access read-write;
          smiv2:oid 1.3.6.1.4.1.1332.1.1.5.3.3.3.1.1.13;
        }

        leaf msanServiceFlowProfileMatchUsEthertype {
          type int32 {
            range "-1..65535";
          }
          description
           "Match upstream packet frame with specified EtherType value.
            A value of -1 indicates that parameter has not been defined.";
          smiv2:defval -1;
          smiv2:max-access read-write;
          smiv2:oid 1.3.6.1.4.1.1332.1.1.5.3.3.3.1.1.14;
        }

        leaf msanServiceFlowProfileMatchUsIpProtocol {
          type int32 {
            range "-1..255";
          }
          description
           "Match upstream packet frame with specified IP protocol value.
            A value of -1 indicates that parameter has not been defined.
            Some of standard protocol values:
               icmp - 1
               igmp - 2
               ip - 4 (ip in ip encapsulation)
               tcp - 6
               udp - 17";
          smiv2:defval -1;
          smiv2:max-access read-write;
          smiv2:oid 1.3.6.1.4.1.1332.1.1.5.3.3.3.1.1.15;
        }

        leaf msanServiceFlowProfileMatchUsIpSrcAddr {
          type inet:ipv4-address;
          description
           "Match upstream packet frame with specified source IP address.
            Empty string indicates that parameter has not been defined.";
          smiv2:defval "";
          smiv2:max-access read-write;
          smiv2:oid 1.3.6.1.4.1.1332.1.1.5.3.3.3.1.1.16;
        }

        leaf msanServiceFlowProfileMatchUsIpSrcMask {
          type inet:ipv4-address;
          description
           "This mask value identifies the portion of msanServiceFlowProfileMatchUsIpSrcAddr
            that is compared with upstream packet.
            Empty string indicates that parameter has not been defined";
          smiv2:defval "";
          smiv2:max-access read-write;
          smiv2:oid 1.3.6.1.4.1.1332.1.1.5.3.3.3.1.1.17;
        }

        leaf msanServiceFlowProfileMatchUsIpDestAddr {
          type inet:ipv4-address;
          description
           "Match upstream packet frame with specified destination IP address.
            Empty string indicates that parameter has not been defined.";
          smiv2:defval "";
          smiv2:max-access read-write;
          smiv2:oid 1.3.6.1.4.1.1332.1.1.5.3.3.3.1.1.18;
        }

        leaf msanServiceFlowProfileMatchUsIpDestMask {
          type inet:ipv4-address;
          description
           "This mask value identifies the portion of msanServiceFlowProfileMatchUsIpDestAddr
            that is compared with upstream packet.
            Empty string indicates that parameter has not been defined";
          smiv2:defval "";
          smiv2:max-access read-write;
          smiv2:oid 1.3.6.1.4.1.1332.1.1.5.3.3.3.1.1.19;
        }

        leaf msanServiceFlowProfileMatchUsIpDscp {
          type int32 {
            range "-1..63";
          }
          description
           "Match upstream packet frame with specified CSC (Class Selector Code Point) = IP precedence (part of TOS field) value.
            A value of -1 indicates that parameter has not been defined.";
          smiv2:defval -1;
          smiv2:max-access read-write;
          smiv2:oid 1.3.6.1.4.1.1332.1.1.5.3.3.3.1.1.20;
        }

        leaf msanServiceFlowProfileMatchUsIpCsc {
          type int32 {
            range "-1..7";
          }
          description
           "Match upstream packet frame with specified IP precedence (part of TOS field) value.
            A value of -1 indicates that parameter has not been defined.";
          smiv2:defval -1;
          smiv2:max-access read-write;
          smiv2:oid 1.3.6.1.4.1.1332.1.1.5.3.3.3.1.1.21;
        }

        leaf msanServiceFlowProfileMatchUsIpDropPrecedence {
          type enumeration {
            enum notDefined {
              value -1;
            }
            enum noDrop {
              value 0;
            }
            enum lowDrop {
              value 1;
            }
            enum mediumDrop {
              value 2;
            }
            enum highDrop {
              value 3;
            }
          }
          description
           "Match upstream packet frame with specified Drop precedence two bits value:
            noDrop(0)          -> 00
            lowDrop(1)         -> 01
            mediumDrop(2)      -> 10
            highDrop(3)        -> 11
            
            A value of -1 indicates that parameter has not been defined.";
          smiv2:defval notDefined;
          smiv2:max-access read-write;
          smiv2:oid 1.3.6.1.4.1.1332.1.1.5.3.3.3.1.1.22;
        }

        leaf msanServiceFlowProfileMatchUsTcpSrcPort {
          type int32 {
            range "-1..65535";
          }
          description
           "Match upstream packet frame with specified source TCP port number.
            A value of -1 indicates that parameter has not been defined.";
          smiv2:defval -1;
          smiv2:max-access read-write;
          smiv2:oid 1.3.6.1.4.1.1332.1.1.5.3.3.3.1.1.23;
        }

        leaf msanServiceFlowProfileMatchUsTcpDestPort {
          type int32 {
            range "-1..65535";
          }
          description
           "Match upstream packet frame with specified destination TCP port number.
            A value of -1 indicates that parameter has not been defined.";
          smiv2:defval -1;
          smiv2:max-access read-write;
          smiv2:oid 1.3.6.1.4.1.1332.1.1.5.3.3.3.1.1.24;
        }

        leaf msanServiceFlowProfileMatchUsUdpSrcPort {
          type int32 {
            range "-1..65535";
          }
          description
           "Match upstream packet frame with specified source UDP port number.
            A value of -1 indicates that parameter has not been defined.";
          smiv2:defval -1;
          smiv2:max-access read-write;
          smiv2:oid 1.3.6.1.4.1.1332.1.1.5.3.3.3.1.1.25;
        }

        leaf msanServiceFlowProfileMatchUsUdpDstPort {
          type int32 {
            range "-1..65535";
          }
          description
           "Match upstream packet frame with specified destination UDP port number.
            A value of -1 indicates that parameter has not been defined.";
          smiv2:defval -1;
          smiv2:max-access read-write;
          smiv2:oid 1.3.6.1.4.1.1332.1.1.5.3.3.3.1.1.26;
        }

        leaf msanServiceFlowProfileMatchDsAny {
          type enumeration {
            enum enable {
              value 1;
            }
            enum disable {
              value 2;
            }
          }
          description
           "Match every downstream packet frame.";
          smiv2:defval disable;
          smiv2:max-access read-write;
          smiv2:oid 1.3.6.1.4.1.1332.1.1.5.3.3.3.1.1.27;
        }

        leaf msanServiceFlowProfileMatchDsMacDestAddr {
          type yang:mac-address;
          description
           "Match downstream packet frame with specified destination MAC address.
            Empty string indicates that parameter has not been defined";
          smiv2:defval "";
          smiv2:max-access read-write;
          smiv2:oid 1.3.6.1.4.1.1332.1.1.5.3.3.3.1.1.28;
        }

        leaf msanServiceFlowProfileMatchDsMacDestMask {
          type yang:mac-address;
          description
           "This mask value identifies the portion of msanServiceFlowProfileMatchDsMacDestAddr
            that is compared with downstream packet.
            Empty string indicates that parameter has not been defined";
          smiv2:defval "";
          smiv2:max-access read-write;
          smiv2:oid 1.3.6.1.4.1.1332.1.1.5.3.3.3.1.1.29;
        }

        leaf msanServiceFlowProfileMatchDsMacSrcAddr {
          type yang:mac-address;
          description
           "Match downstream packet frame with specified source MAC address.
            Empty string indicates that parameter has not been defined";
          smiv2:defval "";
          smiv2:max-access read-write;
          smiv2:oid 1.3.6.1.4.1.1332.1.1.5.3.3.3.1.1.30;
        }

        leaf msanServiceFlowProfileMatchDsMacSrcMask {
          type yang:mac-address;
          description
           "This mask value identifies the portion of msanServiceFlowProfileMatchDsMacSrcAddr
            that is compared with downstream packet.
            Empty string indicates that parameter has not been defined";
          smiv2:defval "";
          smiv2:max-access read-write;
          smiv2:oid 1.3.6.1.4.1.1332.1.1.5.3.3.3.1.1.31;
        }

        leaf msanServiceFlowProfileMatchDsCPcp {
          type int32;
          description
           "Match downstream packet frame with specified Customer PCP (Priority Code Point) -
            PCP is also known as class of service (CoS) bits.
            A value of -1 indicates that parameter has not been defined.";
          smiv2:defval -1;
          smiv2:max-access read-write;
          smiv2:oid 1.3.6.1.4.1.1332.1.1.5.3.3.3.1.1.32;
        }

        leaf msanServiceFlowProfileMatchDsSPcp {
          type int32;
          description
           "Match downstream packet frame with specified Service PCP  (Priority Code Point).
            PCP is also known as class of service (CoS) bits.
            A value of -1 indicates that parameter has not been defined.";
          smiv2:defval -1;
          smiv2:max-access read-write;
          smiv2:oid 1.3.6.1.4.1.1332.1.1.5.3.3.3.1.1.33;
        }

        leaf msanServiceFlowProfileMatchDsVlanProfile {
          type enumeration {
            enum enable {
              value 1;
            }
            enum disable {
              value 2;
            }
          }
          description
           "Match downstream packet frame with VLAN Id values from VLAN Service Profile (msanVlanProfileTable).";
          smiv2:defval disable;
          smiv2:max-access read-write;
          smiv2:oid 1.3.6.1.4.1.1332.1.1.5.3.3.3.1.1.34;
        }

        leaf msanServiceFlowProfileMatchDsCVlanIdRange {
          type binary {
            length "0..512";
          }
          description
           "Match downstream packet frame with specified list (bitmask) of Customer VLAN Id.
            An emptya string indicates that parameter has not been defined.";
          smiv2:defval "";
          smiv2:max-access read-write;
          smiv2:oid 1.3.6.1.4.1.1332.1.1.5.3.3.3.1.1.35;
        }

        leaf msanServiceFlowProfileMatchDsSVlanIdRange {
          type binary {
            length "0..512";
          }
          description
           "Match downstream packet frame with specified list (bitmask) of Service VLAN Id.
            An empty string indicates that parameter has not been defined.";
          smiv2:defval "";
          smiv2:max-access read-write;
          smiv2:oid 1.3.6.1.4.1.1332.1.1.5.3.3.3.1.1.36;
        }

        leaf msanServiceFlowProfileMatchDsEthertype {
          type int32 {
            range "-1..65535";
          }
          description
           "Match downstream packet frame with specified EtherType value.
            A value of -1 indicates that parameter has not been defined.";
          smiv2:defval -1;
          smiv2:max-access read-write;
          smiv2:oid 1.3.6.1.4.1.1332.1.1.5.3.3.3.1.1.37;
        }

        leaf msanServiceFlowProfileMatchDsIpProtocol {
          type int32 {
            range "-1..255";
          }
          description
           "Match downstream packet frame with specified IP protocol value.
            A value of -1 indicates that parameter has not been defined.
            Some of standard protocol values:
               icmp - 1
               igmp - 2
               ip - 4 (ip in ip encapsulation)
               tcp - 6
               udp - 17";
          smiv2:defval -1;
          smiv2:max-access read-write;
          smiv2:oid 1.3.6.1.4.1.1332.1.1.5.3.3.3.1.1.38;
        }

        leaf msanServiceFlowProfileMatchDsIpSrcAddr {
          type inet:ipv4-address;
          description
           "Match downstream packet frame with specified source IP address.
            Empty string indicates that parameter has not been defined.";
          smiv2:defval "";
          smiv2:max-access read-write;
          smiv2:oid 1.3.6.1.4.1.1332.1.1.5.3.3.3.1.1.39;
        }

        leaf msanServiceFlowProfileMatchDsIpSrcMask {
          type inet:ipv4-address;
          description
           "This mask value identifies the portion of msanServiceFlowProfileMatchDsIpSrcAddr
            that is compared with downstream packet.
            Empty string indicates that parameter has not been defined";
          smiv2:defval "";
          smiv2:max-access read-write;
          smiv2:oid 1.3.6.1.4.1.1332.1.1.5.3.3.3.1.1.40;
        }

        leaf msanServiceFlowProfileMatchDsIpDestAddr {
          type inet:ipv4-address;
          description
           "Match downstream packet frame with specified destination IP address.
            Empty string indicates that parameter has not been defined.";
          smiv2:defval "";
          smiv2:max-access read-write;
          smiv2:oid 1.3.6.1.4.1.1332.1.1.5.3.3.3.1.1.41;
        }

        leaf msanServiceFlowProfileMatchDsIpDestMask {
          type inet:ipv4-address;
          description
           "This mask value identifies the portion of msanServiceFlowProfileMatchDsIpDestAddr
            that is compared with downstream packet.
            Empty string indicates that parameter has not been defined";
          smiv2:defval "";
          smiv2:max-access read-write;
          smiv2:oid 1.3.6.1.4.1.1332.1.1.5.3.3.3.1.1.42;
        }

        leaf msanServiceFlowProfileMatchDsIpDscp {
          type int32 {
            range "-1..63";
          }
          description
           "Match downstream packet frame with specified IP DSCP value.
            A value of -1 indicates that parameter has not been defined.";
          smiv2:defval -1;
          smiv2:max-access read-write;
          smiv2:oid 1.3.6.1.4.1.1332.1.1.5.3.3.3.1.1.43;
        }

        leaf msanServiceFlowProfileMatchDsIpCsc {
          type int32 {
            range "-1..7";
          }
          description
           "Match downstream packet frame with specified CSC (Class Selector Code Point) = IP precedence (part of TOS field) value.
            A value of -1 indicates that parameter has not been defined.";
          smiv2:defval -1;
          smiv2:max-access read-write;
          smiv2:oid 1.3.6.1.4.1.1332.1.1.5.3.3.3.1.1.44;
        }

        leaf msanServiceFlowProfileMatchDsIpDropPrecedence {
          type enumeration {
            enum notDefined {
              value -1;
            }
            enum noDrop {
              value 0;
            }
            enum lowDrop {
              value 1;
            }
            enum mediumDrop {
              value 2;
            }
            enum highDrop {
              value 3;
            }
          }
          description
           "Match downstream packet frame with specified Drop precedence two bits value:
            noDrop(0)          -> 00
            lowDrop(1)         -> 01
            mediumDrop(2)      -> 10
            highDrop(3)        -> 11
            
            A value of -1 indicates that parameter has not been defined.";
          smiv2:defval notDefined;
          smiv2:max-access read-write;
          smiv2:oid 1.3.6.1.4.1.1332.1.1.5.3.3.3.1.1.45;
        }

        leaf msanServiceFlowProfileMatchDsTcpSrcPort {
          type int32 {
            range "-1..65535";
          }
          description
           "Match downstream packet frame with specified source TCP port number.
            A value of -1 indicates that parameter has not been defined.";
          smiv2:defval -1;
          smiv2:max-access read-write;
          smiv2:oid 1.3.6.1.4.1.1332.1.1.5.3.3.3.1.1.46;
        }

        leaf msanServiceFlowProfileMatchDsTcpDestPort {
          type int32 {
            range "-1..65535";
          }
          description
           "Match downstream packet frame with specified destination TCP port number.
            A value of -1 indicates that parameter has not been defined.";
          smiv2:defval -1;
          smiv2:max-access read-write;
          smiv2:oid 1.3.6.1.4.1.1332.1.1.5.3.3.3.1.1.47;
        }

        leaf msanServiceFlowProfileMatchDsUdpSrcPort {
          type int32 {
            range "-1..65535";
          }
          description
           "Match downstream packet frame with specified source UDP port number.
            A value of -1 indicates that parameter has not been defined.";
          smiv2:defval -1;
          smiv2:max-access read-write;
          smiv2:oid 1.3.6.1.4.1.1332.1.1.5.3.3.3.1.1.48;
        }

        leaf msanServiceFlowProfileMatchDsUdpDstPort {
          type int32 {
            range "-1..65535";
          }
          description
           "Match downstream packet frame with specified destination UDP port number.
            A value of -1 indicates that parameter has not been defined.";
          smiv2:defval -1;
          smiv2:max-access read-write;
          smiv2:oid 1.3.6.1.4.1.1332.1.1.5.3.3.3.1.1.49;
        }

        leaf msanServiceFlowProfileUsCdr {
          type int32 {
            range "0..1000000";
          }
          units kbps;
          description
           "Upstream committed data rate (E-CDR) in kbps (0 � 1000000).";
          smiv2:defval 0;
          smiv2:max-access read-write;
          smiv2:oid 1.3.6.1.4.1.1332.1.1.5.3.3.3.1.1.50;
        }

        leaf msanServiceFlowProfileUsCdrBurstSize {
          type int32 {
            range "0..16384";
          }
          units kB;
          description
           "Upstream committed data rate burst size in kB (0 � 16384).
            
            When parameter is set to 0 (default), it's automatically updated to default
            burst size in according with current msanQoSProfileInCdr value.";
          smiv2:defval 0;
          smiv2:max-access read-write;
          smiv2:oid 1.3.6.1.4.1.1332.1.1.5.3.3.3.1.1.51;
        }

        leaf msanServiceFlowProfileUsPdr {
          type int32 {
            range "0..1000000";
          }
          units kbps;
          description
           "Upstream peak data rate (E-PDR) in kbps (0 � 1000000).";
          smiv2:defval 0;
          smiv2:max-access read-write;
          smiv2:oid 1.3.6.1.4.1.1332.1.1.5.3.3.3.1.1.52;
        }

        leaf msanServiceFlowProfileUsPdrBurstSize {
          type int32 {
            range "0..16384";
          }
          units kB;
          description
           "Upstream peak data rate burst size in kB (0 � 16384).
            
            When parameter is set to 0 (default), it's automatically updated to default
            burst size in according with current msanQoSProfileInPdr value.";
          smiv2:defval 0;
          smiv2:max-access read-write;
          smiv2:oid 1.3.6.1.4.1.1332.1.1.5.3.3.3.1.1.53;
        }

        leaf msanServiceFlowProfileUsMarkPcp {
          type enumeration {
            enum none {
              value 1;
            }
            enum copyFromCsc {
              value 2;
            }
            enum userValue {
              value 3;
            }
          }
          description
           "Type of upstrem PCP marking.
            If set to userValue(3), parameter msanServiceFlowProfileUsMarkPcpValue is used.
            A value of none(1) indicates that parameter has not been defined";
          smiv2:defval none;
          smiv2:max-access read-write;
          smiv2:oid 1.3.6.1.4.1.1332.1.1.5.3.3.3.1.1.54;
        }

        leaf msanServiceFlowProfileUsMarkPcpValue {
          type int32 {
            range "-1..7";
          }
          description
           "Mark upstream packets with specified PCP (Priority Code Point) value (0-7) = CoS.
            A value of -1 indicates that parameter has not been defined";
          smiv2:defval -1;
          smiv2:max-access read-write;
          smiv2:oid 1.3.6.1.4.1.1332.1.1.5.3.3.3.1.1.55;
        }

        leaf msanServiceFlowProfileUsMarkDscp {
          type enumeration {
            enum none {
              value 1;
            }
            enum copyFromPcp {
              value 2;
            }
            enum userValue {
              value 3;
            }
          }
          description
           "Type of upstrem DSCP marking.
            If set to userValue(3), parameter msanServiceFlowProfileUsMarkDscpValue is used.
            A value of none(1) indicates that parameter has not been defined";
          smiv2:defval none;
          smiv2:max-access read-write;
          smiv2:oid 1.3.6.1.4.1.1332.1.1.5.3.3.3.1.1.56;
        }

        leaf msanServiceFlowProfileUsMarkDscpValue {
          type int32 {
            range "-1..63";
          }
          description
           "Mark upstream packets with specified DSCP (Diffserv Code Point) value (0-63).
            A value of -1 indicates that parameter has not been defined";
          smiv2:defval -1;
          smiv2:max-access read-write;
          smiv2:oid 1.3.6.1.4.1.1332.1.1.5.3.3.3.1.1.57;
        }

        leaf msanServiceFlowProfileDsCdr {
          type int32 {
            range "0..1000000";
          }
          units kbps;
          description
           "Downstream committed data rate (E-CDR) in kbps (0 � 1000000).";
          smiv2:defval 0;
          smiv2:max-access read-write;
          smiv2:oid 1.3.6.1.4.1.1332.1.1.5.3.3.3.1.1.58;
        }

        leaf msanServiceFlowProfileDsCdrBurstSize {
          type int32 {
            range "0..16384";
          }
          units kB;
          description
           "Downstream committed data rate burst size in kB (0 � 16384).
            
            When parameter is set to 0 (default), it's automatically updated to default
            burst size in according with current msanQoSProfileOutCdr value.";
          smiv2:defval 0;
          smiv2:max-access read-write;
          smiv2:oid 1.3.6.1.4.1.1332.1.1.5.3.3.3.1.1.59;
        }

        leaf msanServiceFlowProfileDsPdr {
          type int32 {
            range "0..1000000";
          }
          units kbps;
          description
           "Downstream peak data rate (E-PDR) in kbps (0 � 1000000).";
          smiv2:defval 0;
          smiv2:max-access read-write;
          smiv2:oid 1.3.6.1.4.1.1332.1.1.5.3.3.3.1.1.60;
        }

        leaf msanServiceFlowProfileDsPdrBurstSize {
          type int32 {
            range "0..16384";
          }
          units kB;
          description
           "Downstream peak data rate burst size in kB (0 � 16384).
            
            When parameter is set to 0 (default), it's automatically updated to default
            burst size in according with current msanQoSProfileOutCdr value.";
          smiv2:defval 0;
          smiv2:max-access read-write;
          smiv2:oid 1.3.6.1.4.1.1332.1.1.5.3.3.3.1.1.61;
        }

        leaf msanServiceFlowProfileDsMarkPcp {
          type enumeration {
            enum none {
              value 1;
            }
            enum copyFromCsc {
              value 2;
            }
            enum userValue {
              value 3;
            }
          }
          description
           "Type of downstream  PCP marking.
            If set to userValue(3), parameter msanServiceFlowProfileDsMarkPcpValue is used.
            A value of none(1) indicates that parameter has not been defined";
          smiv2:defval none;
          smiv2:max-access read-write;
          smiv2:oid 1.3.6.1.4.1.1332.1.1.5.3.3.3.1.1.62;
        }

        leaf msanServiceFlowProfileDsMarkPcpValue {
          type int32 {
            range "-1..7";
          }
          description
           "Mark downstream packets with specified PCP (Priority Code Point) value (0-7) = CoS.
            A value of -1 indicates that parameter has not been defined";
          smiv2:defval -1;
          smiv2:max-access read-write;
          smiv2:oid 1.3.6.1.4.1.1332.1.1.5.3.3.3.1.1.63;
        }

        leaf msanServiceFlowProfileDsMarkDscp {
          type enumeration {
            enum none {
              value 1;
            }
            enum copyFromPcp {
              value 2;
            }
            enum userValue {
              value 3;
            }
          }
          description
           "Type of downstrem DSCP marking.
            If set to userValue(3), parameter msanServiceFlowProfileDsMarkDscpValue is used.
            A value of none(1) indicates that parameter has not been defined";
          smiv2:defval none;
          smiv2:max-access read-write;
          smiv2:oid 1.3.6.1.4.1.1332.1.1.5.3.3.3.1.1.64;
        }

        leaf msanServiceFlowProfileDsMarkDscpValue {
          type int32 {
            range "-1..63";
          }
          description
           "Mark downstream packets with specified DSCP (Diffserv Code Point) value (0-63).
            A value of -1 indicates that parameter has not been defined";
          smiv2:defval -1;
          smiv2:max-access read-write;
          smiv2:oid 1.3.6.1.4.1.1332.1.1.5.3.3.3.1.1.65;
        }

        leaf msanServiceFlowProfileDsQueuingPriority {
          type int32 {
            range "0..7";
          }
          description
           "Queuing Priority of Service Flow Profile. ";
          smiv2:defval 0;
          smiv2:max-access read-write;
          smiv2:oid 1.3.6.1.4.1.1332.1.1.5.3.3.3.1.1.66;
        }

        leaf msanServiceFlowProfileDsSchedulingMode {
          type enumeration {
            enum weighted {
              value 1;
            }
            enum strict {
              value 2;
            }
          }
          description
           "Scheduling Mode";
          smiv2:defval weighted;
          smiv2:max-access read-write;
          smiv2:oid 1.3.6.1.4.1.1332.1.1.5.3.3.3.1.1.67;
        }
        leaf msanServiceFlowProfileMatchUsIpv6SrcAddr {
          type inet-address:InetAddressIPv6;
          description
           "Match upstream packet frame with specified source IPv6 address.
            Empty string indicates that parameter has not been defined.";
          smiv2:defval "";
          smiv2:max-access read-write;
          smiv2:oid 1.3.6.1.4.1.1332.1.1.5.3.3.3.1.1.70;
        }

        leaf msanServiceFlowProfileMatchUsIpv6SrcAddrMaskLen {
          type int32 {
            range "0..128";
          }
          description
           "This mask value identifies the portion of msanServiceFlowProfileMatchUsIpv6SrcAddr
            that is compared with upstream packet.";
          smiv2:defval 0;
          smiv2:max-access read-write;
          smiv2:oid 1.3.6.1.4.1.1332.1.1.5.3.3.3.1.1.71;
        }

        leaf msanServiceFlowProfileMatchUsIpv6DestAddr {
          type inet-address:InetAddressIPv6;
          description
           "Match upstream packet frame with specified destination IPv6 address.
            Empty string indicates that parameter has not been defined.";
          smiv2:defval "";
          smiv2:max-access read-write;
          smiv2:oid 1.3.6.1.4.1.1332.1.1.5.3.3.3.1.1.72;
        }

        leaf msanServiceFlowProfileMatchUsIpv6DestAddrMaskLen {
          type int32 {
            range "0..128";
          }
          description
           "This mask value identifies the portion of msanServiceFlowProfileMatchUsIpv6DestAddr
            that is compared with upstream packet.";
          smiv2:defval 0;
          smiv2:max-access read-write;
          smiv2:oid 1.3.6.1.4.1.1332.1.1.5.3.3.3.1.1.73;
        }

        leaf msanServiceFlowProfileMatchDsIpv6SrcAddr {
          type inet-address:InetAddressIPv6;
          description
           "Match downstream packet frame with specified source IPv6 address.
            Empty string indicates that parameter has not been defined.";
          smiv2:defval "";
          smiv2:max-access read-write;
          smiv2:oid 1.3.6.1.4.1.1332.1.1.5.3.3.3.1.1.74;
        }

        leaf msanServiceFlowProfileMatchDsIpv6SrcAddrMaskLen {
          type int32 {
            range "0..128";
          }
          description
           "This mask value identifies the portion of msanServiceFlowProfileMatchDsIpv6SrcAddr
            that is compared with downstream packet.";
          smiv2:defval 0;
          smiv2:max-access read-write;
          smiv2:oid 1.3.6.1.4.1.1332.1.1.5.3.3.3.1.1.75;
        }

        leaf msanServiceFlowProfileMatchDsIpv6DestAddr {
          type inet-address:InetAddressIPv6;
          description
           "Match downstream packet frame with specified destination IPv6 address.
            Empty string indicates that parameter has not been defined.";
          smiv2:defval "";
          smiv2:max-access read-write;
          smiv2:oid 1.3.6.1.4.1.1332.1.1.5.3.3.3.1.1.76;
        }

        leaf msanServiceFlowProfileMatchDsIpv6DestAddrMaskLen {
          type int32 {
            range "0..128";
          }
          description
           "This mask value identifies the portion of msanServiceFlowProfileMatchDsIpv6DestAddr
            that is compared with downstrem packet.";
          smiv2:defval 0;
          smiv2:max-access read-write;
          smiv2:oid 1.3.6.1.4.1.1332.1.1.5.3.3.3.1.1.77;
        }
                leaf msanServiceFlowProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanVlanProfileTable {
      description
       "Vlan Profile table ";
      smiv2:oid 1.3.6.1.4.1.1332.1.1.5.3.3.4.1;

      list msanVlanProfileEntry {
        key msanVlanProfileName;
        description
         "Vlan Profile table entry.";
        smiv2:oid 1.3.6.1.4.1.1332.1.1.5.3.3.4.1.1;

        leaf msanVlanProfileName {
          type rfc1213-mib:DisplayString {
            length "1..32";
          }
          description
           "Name for the VLAN profile.";
          smiv2:max-access not-accessible;
          smiv2:oid 1.3.6.1.4.1.1332.1.1.5.3.3.4.1.1.1;
        }

        leaf msanVlanProfileCVid {
          type binary {
            length "0..512";
          }
          description
           "Customer VLANs Identification (bit mask).";
          smiv2:defval "";
          smiv2:max-access read-write;
          smiv2:oid 1.3.6.1.4.1.1332.1.1.5.3.3.4.1.1.4;
        }

        leaf msanVlanProfileCVidNative {
          type int32 {
            range "-1..4094";
          }
          description
           "Nativ C-VLAN Id.
            A value of -1 indicates that parameter has not been defined.";
          smiv2:defval -1;
          smiv2:max-access read-write;
          smiv2:oid 1.3.6.1.4.1.1332.1.1.5.3.3.4.1.1.5;
        }

        leaf msanVlanProfileCVidRemark {
          type int32 {
            range "-1..4094";
          }
          description
           "Remark C-VLAN Id.
            A value of -1 indicates that parameter has not been defined.";
          smiv2:defval -1;
          smiv2:max-access read-write;
          smiv2:oid 1.3.6.1.4.1.1332.1.1.5.3.3.4.1.1.6;
        }

        leaf msanVlanProfileSVid {
          type int32 {
            range "-1..4094";
          }
          description
           "S-VLAN Id.
            A value of -1 indicates that parameter has not been defined.";
          smiv2:defval -1;
          smiv2:max-access read-write;
          smiv2:oid 1.3.6.1.4.1.1332.1.1.5.3.3.4.1.1.7;
        }

        leaf msanVlanProfileSEtherType {
          type int32;
          description
           "Ether Type value. ";
          smiv2:defval 34984;
          smiv2:max-access read-write;
          smiv2:oid 1.3.6.1.4.1.1332.1.1.5.3.3.4.1.1.8;
        }

        leaf msanVlanProfileNetworkPortCTag {
          type enumeration {
            enum use {
              value 1;
            }
            enum notUse {
              value 2;
            }
          }
          description
           "Usage of C-VLAN tag on network port.
            If assigned as notUse(2) in upstream direction, C-VLAN tag is removed.";
          smiv2:defval use;
          smiv2:max-access read-write;
          smiv2:oid 1.3.6.1.4.1.1332.1.1.5.3.3.4.1.1.12;
        }
                leaf msanVlanProfileUsage {
                    type enumeration {
                        enum attached {
                            value 1;
                        }
                        enum notAttached {
                            value 2;
                        }
                    }
                    config false;
                    status current;
                    description 
                        "Profile usage.
                         If profile is attached,  profile values can't be edited.
                         ";
                }
                leaf msanVlanProfileCVidExternal {
                    type enumeration {
                        enum enable {
                            value 1;
                        }
                        enum disable {
                            value 2;
                        }
                    }
                    description "Use external parameter msanProfilePortDataCVid as C-VLAN Id.";
                }
                leaf msanVlanProfileCVidNativeExternal {
                    type enumeration {
                        enum enable {
                            value 1;
                        }
                        enum disable {
                            value 2;
                        }
                    }
                    description "Use external parameter msanProfilePortDataCVid as Native C-VLAN Id.";
                }
                leaf msanVlanProfileCVidRemarkExternal {
                    type enumeration {
                        enum enable {
                            value 1;
                        }
                        enum disable {
                            value 2;
                        }
                    }
                    description "Use external parameter msanProfilePortDataCVid as Remark C-VLAN Id.";
                }
                leaf msanVlanProfileSVidExternal {
                    type enumeration {
                        enum enable {
                            value 1;
                        }
                        enum disable {
                            value 2;
                        }
                    }
                    description "Use external parameter msanProfilePortDataCVid as  S-VLAN Id.";
                }


      }
    }

    container msanVlanPortProfileTable {
      description
       "A connection between VLAN profiles and device ports";
      smiv2:oid 1.3.6.1.4.1.1332.1.1.5.3.3.4.2;

      list msanVlanPortProfileEntry {
        key "ifName msanVlanProfileName";
        description
         "Service Profile Port table entry.";
        smiv2:oid 1.3.6.1.4.1.1332.1.1.5.3.3.4.2.1;

        leaf ifName {
          type if:interface-ref;
          description
            "A reference to the name of a configured network layer
             interface.";
        }

        leaf msanVlanProfileName {
          type leafref {
            path "/iskratel-msan:ISKRATEL-MSAN-MIB/iskratel-msan:msanVlanProfileTable/iskratel-msan:msanVlanProfileEntry/iskratel-msan:msanVlanProfileName";
          }
        }
      }
    }

    container msanMulticastProfileTable {
      description
       "Multicast Profile table ";
      smiv2:oid 1.3.6.1.4.1.1332.1.1.5.3.3.5.1;

      list msanMulticastProfileEntry {
        key msanMulticastProfileName;
        description
         "Multicast Profile table entry.";
        smiv2:oid 1.3.6.1.4.1.1332.1.1.5.3.3.5.1.1;

        leaf msanMulticastProfileName {
          type rfc1213-mib:DisplayString {
            length "1..32";
          }
          description
           "Name for the Multicast profile.";
          smiv2:max-access not-accessible;
          smiv2:oid 1.3.6.1.4.1.1332.1.1.5.3.3.5.1.1.1;
        }

        leaf msanMulticastProfileIgmpSnooping {
          type enumeration {
            enum disableAndDiscard {
              value 0;
            }
            enum enable {
              value 1;
            }
            enum enableAndUnknownGroupFlood {
              value 2;
            }
            enum disableAndBroadcast {
              value 3;
            }
          }
          description
           "IGMP snnoping";
          smiv2:defval disableAndDiscard;
          smiv2:max-access read-write;
          smiv2:oid 1.3.6.1.4.1.1332.1.1.5.3.3.5.1.1.4;
        }

        leaf msanMulticastProfileIgmpSnoopingFastLeave {
          type enumeration {
            enum disable {
              value 0;
            }
            enum enable {
              value 1;
            }
          }
          description
           "IGMP Snooping Fast Leave.";
          smiv2:defval disable;
          smiv2:max-access read-write;
          smiv2:oid 1.3.6.1.4.1.1332.1.1.5.3.3.5.1.1.5;
        }

        leaf msanMulticastProfileIgmpSnoopingSuppression {
          type enumeration {
            enum disable {
              value 0;
            }
            enum enable {
              value 1;
            }
          }
          description
           "IGMP Snooping Suppression.";
          smiv2:defval disable;
          smiv2:max-access read-write;
          smiv2:oid 1.3.6.1.4.1.1332.1.1.5.3.3.5.1.1.6;
        }

        leaf msanMulticastProfileIgmpProxy {
          type enumeration {
            enum disable {
              value 0;
            }
            enum enable {
              value 1;
            }
          }
          description
           "IGMP proxy.";
          smiv2:defval disable;
          smiv2:max-access read-write;
          smiv2:oid 1.3.6.1.4.1.1332.1.1.5.3.3.5.1.1.7;
        }

        leaf msanMulticastProfileIgmpProxyIpAddress {
          type inet:ipv4-address;
          description
           "IGMP proxy IP address.";
          smiv2:max-access read-write;
          smiv2:oid 1.3.6.1.4.1.1332.1.1.5.3.3.5.1.1.8;
        }

        leaf msanMulticastProfileIgmpFiltering {
          type enumeration {
            enum allowAll {
              value 0;
            }
            enum allowReports {
              value 1;
            }
            enum allowQueries {
              value 2;
            }
            enum dropAll {
              value 3;
            }
          }
          description
           "IGMP filtering.";
          smiv2:defval allowReports;
          smiv2:max-access read-write;
          smiv2:oid 1.3.6.1.4.1.1332.1.1.5.3.3.5.1.1.9;
        }

        leaf msanMulticastProfileMulticastGroupLimit {
          type uint32 {
            range "0..10";
          }
          description
           "Multicast group limit.
            A value of 0 indicates not limit.";
          smiv2:defval 0;
          smiv2:max-access read-write;
          smiv2:oid 1.3.6.1.4.1.1332.1.1.5.3.3.5.1.1.10;
        }

        leaf msanMulticastProfileMvr {
          type enumeration {
            enum disable {
              value 0;
            }
            enum enable {
              value 1;
            }
          }
          description
           "Multicast VLAN Registration.";
          smiv2:defval disable;
          smiv2:max-access read-write;
          smiv2:oid 1.3.6.1.4.1.1332.1.1.5.3.3.5.1.1.11;
        }

        leaf msanMulticastProfileIgmpProxyProtocolVersion {
          type enumeration {
            enum useGlobalIgmpSettings {
              value 1;
            }
            enum igmpv2 {
              value 2;
            }
            enum igmpv3 {
              value 3;
            }
          }
          description
           "IGMP version of IGMP message sent by Proxy in downstream direction.";
          smiv2:defval useGlobalIgmpSettings;
          smiv2:max-access read-write;
          smiv2:oid 1.3.6.1.4.1.1332.1.1.5.3.3.5.1.1.14;
        }
                leaf msanMulticastProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanMulticastProfileStaticGroupTable {
      description
       "Connection between
        multicast_profile and multicast_static_group table ";
      smiv2:oid 1.3.6.1.4.1.1332.1.1.5.3.3.5.2;

      list msanMulticastProfileStaticGroupEntry {
        key "msanMulticastProfileName msanMulticastProfileStaticGroupIpAddr";
        description
         "Multicast Profile Group table entry.";
        smiv2:oid 1.3.6.1.4.1.1332.1.1.5.3.3.5.2.1;

        leaf msanMulticastProfileName {
          type leafref {
            path "/iskratel-msan:ISKRATEL-MSAN-MIB/iskratel-msan:msanMulticastProfileTable/iskratel-msan:msanMulticastProfileEntry/iskratel-msan:msanMulticastProfileName";
          }
        }

        leaf msanMulticastProfileStaticGroupIpAddr {
          type inet:ipv4-address;
          description
           "Description.";
          smiv2:max-access not-accessible;
          smiv2:oid 1.3.6.1.4.1.1332.1.1.5.3.3.5.2.1.1;
        }
      }
    }

    container msanSecurityProfileTable {
      description
       "Security Profile table ";
      smiv2:oid 1.3.6.1.4.1.1332.1.1.5.3.3.6.1;

      list msanSecurityProfileEntry {
        key msanSecurityProfileName;
        description
         "Security Profile table entry.";
        smiv2:oid 1.3.6.1.4.1.1332.1.1.5.3.3.6.1.1;

        leaf msanSecurityProfileName {
          type rfc1213-mib:DisplayString {
            length "1..32";
          }
          description
           "Name of the security profile.";
          smiv2:max-access not-accessible;
          smiv2:oid 1.3.6.1.4.1.1332.1.1.5.3.3.6.1.1.1;
        }

        leaf msanSecurityProfileProtectedPort {
          type enumeration {
            enum disable {
              value 0;
            }
            enum enable {
              value 1;
            }
          }
          description
           "Security profile protected port";
          smiv2:defval disable;
          smiv2:max-access read-write;
          smiv2:oid 1.3.6.1.4.1.1332.1.1.5.3.3.6.1.1.4;
        }

        leaf msanSecurityProfileMacSg {
          type enumeration {
            enum disable {
              value 0;
            }
            enum enable {
              value 1;
            }
          }
          description
           "Mac source guard";
          smiv2:defval disable;
          smiv2:max-access read-write;
          smiv2:oid 1.3.6.1.4.1.1332.1.1.5.3.3.6.1.1.5;
        }

        leaf msanSecurityProfileMacLimit {
          type uint32 {
            range "0..64";
          }
          description
           "MAC limit
            A value of 0 indicates that parameter has not been defined.";
          smiv2:defval 0;
          smiv2:max-access read-write;
          smiv2:oid 1.3.6.1.4.1.1332.1.1.5.3.3.6.1.1.6;
        }

        leaf msanSecurityProfilePortSecurity {
          type enumeration {
            enum disable {
              value 0;
            }
            enum enable {
              value 1;
            }
          }
          description
           "Port security";
          smiv2:defval disable;
          smiv2:max-access read-write;
          smiv2:oid 1.3.6.1.4.1.1332.1.1.5.3.3.6.1.1.7;
        }

        leaf msanSecurityProfileIpSg {
          type enumeration {
            enum disable {
              value 0;
            }
            enum enable {
              value 1;
            }
          }
          description
           "IP source guard";
          smiv2:defval disable;
          smiv2:max-access read-write;
          smiv2:oid 1.3.6.1.4.1.1332.1.1.5.3.3.6.1.1.8;
        }

        leaf msanSecurityProfileIpSgBindingLimit {
          type uint32 {
            range "0..15";
          }
          description
           "IP source guard binding limit.
            Value 0 defines there is no limit.";
          smiv2:defval 4;
          smiv2:max-access read-write;
          smiv2:oid 1.3.6.1.4.1.1332.1.1.5.3.3.6.1.1.9;
        }

        leaf msanSecurityProfileIpSgFilteringMode {
          type enumeration {
            enum ipSourceAddress {
              value 1;
            }
            enum ipAndMacSourceAddress {
              value 2;
            }
          }
          description
           "IP source guard filtering mode";
          smiv2:defval ipAndMacSourceAddress;
          smiv2:max-access read-write;
          smiv2:oid 1.3.6.1.4.1.1332.1.1.5.3.3.6.1.1.10;
        }

        leaf msanSecurityProfileArpInspec {
          type enumeration {
            enum disable {
              value 0;
            }
            enum enable {
              value 1;
            }
          }
          description
           "Dynamic ARP inspection";
          smiv2:defval disable;
          smiv2:max-access read-write;
          smiv2:oid 1.3.6.1.4.1.1332.1.1.5.3.3.6.1.1.12;
        }

        leaf msanSecurityProfileMacForward {
          type enumeration {
            enum disable {
              value 0;
            }
            enum enable {
              value 1;
            }
          }
          description
           "MAC forwarding";
          smiv2:defval disable;
          smiv2:max-access read-write;
          smiv2:oid 1.3.6.1.4.1.1332.1.1.5.3.3.6.1.1.13;
        }

        leaf msanSecurityProfileIpSgIpv6 {
          type enumeration {
            enum disable {
              value 0;
            }
            enum enable {
              value 1;
            }
          }
          description
           "IPv6 source guard";
          smiv2:defval disable;
          smiv2:max-access read-write;
          smiv2:oid 1.3.6.1.4.1.1332.1.1.5.3.3.6.1.1.16;
        }

        leaf msanSecurityProfileIpSgBindingLimitDhcpv6 {
          type uint32 {
            range "0..15";
          }
          description
           "IPSG binding limit for DHCPv6 (IPv6 DHCP).
            Value 0 defines there is no limit.";
          smiv2:defval 4;
          smiv2:max-access read-write;
          smiv2:oid 1.3.6.1.4.1.1332.1.1.5.3.3.6.1.1.17;
        }

        leaf msanSecurityProfileIpSgBindingLimitND {
          type uint32 {
            range "0..15";
          }
          description
           "IPSG binding limit for ND (IPv6 Neighbor Discovery).
            Value 0 defines there is no limit.";
          smiv2:defval 4;
          smiv2:max-access read-write;
          smiv2:oid 1.3.6.1.4.1.1332.1.1.5.3.3.6.1.1.18;
        }

        leaf msanSecurityProfileStormControlBroadcast {
          type int32 {
            range "-1..65535";
          }
          units pps;
          description
           "Max data rate (pps)  of broadcast packets on port at which storm control drops them.
            Value -1 defines that functionality is disabled.";
          smiv2:defval -1;
          smiv2:max-access read-write;
          smiv2:oid 1.3.6.1.4.1.1332.1.1.5.3.3.6.1.1.19;
        }

        leaf msanSecurityProfileStormControlMulticast {
          type int32 {
            range "-1..65535";
          }
          units pps;
          description
           "Max data rate (pps)  of multicast packets on port at which storm control drops them.
            Value -1 defines that functionality is disabled.";
          smiv2:defval -1;
          smiv2:max-access read-write;
          smiv2:oid 1.3.6.1.4.1.1332.1.1.5.3.3.6.1.1.20;
        }

        leaf msanSecurityProfileStormControlUnicast {
          type int32 {
            range "-1..65535";
          }
          units pps;
          description
           "Max data rate (pps)  of unicast packets on port at which storm control drops them.
            Value -1 defines that functionality is disabled.";
          smiv2:defval -1;
          smiv2:max-access read-write;
          smiv2:oid 1.3.6.1.4.1.1332.1.1.5.3.3.6.1.1.21;
        }

        leaf msanSecurityProfileAppRateLimitDhcp {
          type int32 {
            range "-1..1000";
          }
          units pps;
          description
           "Max data rate (pps)  of DHCP packets on port  at which application rate limit drops them.
            Value -1 defines that functionality is disabled.";
          smiv2:defval -1;
          smiv2:max-access read-write;
          smiv2:oid 1.3.6.1.4.1.1332.1.1.5.3.3.6.1.1.22;
        }

        leaf msanSecurityProfileAppRateLimitIgmp {
          type int32 {
            range "-1..1000";
          }
          units pps;
          description
           "Max data rate (pps)  of IGMP packets on port  at which application rate limit drops them.
            Value -1 defines that functionality is disabled.";
          smiv2:defval -1;
          smiv2:max-access read-write;
          smiv2:oid 1.3.6.1.4.1.1332.1.1.5.3.3.6.1.1.23;
        }

        leaf msanSecurityProfileAppRateLimitPppoe {
          type int32 {
            range "-1..1000";
          }
          units pps;
          description
           "Max data rate (pps)  of PPPoE packets on port  at which application rate limit drops them.
            Value -1 defines that functionality is disabled.";
          smiv2:defval -1;
          smiv2:max-access read-write;
          smiv2:oid 1.3.6.1.4.1.1332.1.1.5.3.3.6.1.1.24;
        }

        leaf msanSecurityProfileAppRateLimitStp {
          type int32 {
            range "-1..1000";
          }
          units pps;
          description
           "Max data rate (pps)  of STP packets on port  at which application rate limit drops them.
            Value -1 defines that functionality is disabled.";
          smiv2:defval -1;
          smiv2:max-access read-write;
          smiv2:oid 1.3.6.1.4.1.1332.1.1.5.3.3.6.1.1.25;
        }

        leaf msanSecurityProfileAppRateLimitMn {
          type int32 {
            range "-1..1000";
          }
          units pps;
          description
           "Max data rate (pps)  of IP packets on MN CPU port  at which application rate limit drops them.
            Value -1 defines that functionality is disabled.";
          smiv2:defval -1;
          smiv2:max-access read-write;
          smiv2:oid 1.3.6.1.4.1.1332.1.1.5.3.3.6.1.1.26;
        }
                leaf msanSecurityProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanSecurityAclProfileTable {
      description
       "A connection between security profiles and access lists";
      smiv2:oid 1.3.6.1.4.1.1332.1.1.5.3.3.6.3;

      list msanSecurityAclProfileEntry {
        key "msanSecurityProfileName msanSecurityAclProfileAclDirection msanSecurityAclProfileSequence msanSecurityAclProfileAclIndex msanSecurityAclProfileAclMacName";
        description
         "Service Profile Port table entry.";
        smiv2:oid 1.3.6.1.4.1.1332.1.1.5.3.3.6.3.1;

        leaf msanSecurityProfileName {
          type leafref {
            path "/iskratel-msan:ISKRATEL-MSAN-MIB/iskratel-msan:msanSecurityProfileTable/iskratel-msan:msanSecurityProfileEntry/iskratel-msan:msanSecurityProfileName";
          }
        }

        leaf msanSecurityAclProfileAclDirection {
          type enumeration {
            enum inbound {
              value 1;
            }
            enum outbound {
              value 2;
            }
          }
          description
           "The direction to which this ACL instance applies.";
          smiv2:max-access not-accessible;
          smiv2:oid 1.3.6.1.4.1.1332.1.1.5.3.3.6.3.1.1;
        }

        leaf msanSecurityAclProfileSequence {
          type uint32 {
            range "1..2147483647";
          }
          description
           "The relative evaluation sequence of this ACL for this
            interface and direction.  When multiple ACLs are allowed
            for a given interface and direction, the sequence number
            determines the order in which the list of ACLs are evaluated,
            with lower sequence numbers given higher precedence.  The
            sequence number value is arbitrary, but must be a unique
            non-zero value for a given interface and direction.
            
            Setting this object to an existing sequence number
            value for a given interface and direction causes the
            ACL corresponding to that value to be replaced with this ACL.";
          smiv2:max-access not-accessible;
          smiv2:oid 1.3.6.1.4.1.1332.1.1.5.3.3.6.3.1.2;
        }

        leaf msanSecurityAclProfileAclIndex {
          type uint32;
          description
           "Reference to IP  ACL:
            /iskratel-msan:ISKRATEL-MSAN-BASICCONF-MIB/iskratel-msan:aclTable/iskratel-msan:aclEntry/iskratel-msan:aclIndex
            
            If IP ACL is not used, this parameter has value 0.";
          smiv2:max-access not-accessible;
          smiv2:oid 1.3.6.1.4.1.1332.1.1.5.3.3.6.3.1.4;
        }

        leaf msanSecurityAclProfileAclMacName {
          type rfc1213-mib:DisplayString;
          description
           "Reference to MAC ACL:
            /iskratel-msan:ISKRATEL-MSAN-BASICCONF-MIB/iskratel-msan:aclMacTable/iskratel-msan:aclMacEntry/iskratel-msan:aclMacName
            
            If MAC ACL is not used, this parameter should be empty string.";
          smiv2:max-access not-accessible;
          smiv2:oid 1.3.6.1.4.1.1332.1.1.5.3.3.6.3.1.4;
        }
      }
    }

    container msanL2cpProfileTable {
      description
       "L2CP (Layer 2 Control Protocol) Profile table ";
      smiv2:oid 1.3.6.1.4.1.1332.1.1.5.3.3.7.1;

      list msanL2cpProfileEntry {
        key msanL2cpProfileName;
        description
         "L2cp Profile table entry.";
        smiv2:oid 1.3.6.1.4.1.1332.1.1.5.3.3.7.1.1;

        leaf msanL2cpProfileName {
          type rfc1213-mib:DisplayString {
            length "1..32";
          }
          description
           "Name of the L2CP profile.";
          smiv2:max-access not-accessible;
          smiv2:oid 1.3.6.1.4.1.1332.1.1.5.3.3.7.1.1.1;
        }

        leaf msanL2cpProfileDescription {
          type rfc1213-mib:DisplayString {
            length "0..255";
          }
                    status obsolete;

          description
           "Attribute specifies text which describes the associated object.";
          smiv2:max-access read-write;
          smiv2:oid 1.3.6.1.4.1.1332.1.1.5.3.3.7.1.1.4;
        }
                leaf msanL2cpProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanL2cpProtocolTable {
      description
       "Table with list of L2CP protocols";
      smiv2:oid 1.3.6.1.4.1.1332.1.1.5.3.3.7.2;

      list msanL2cpProtocolEntry {
        key msanL2cpProtocolName;
        description
         "Description.";
        smiv2:oid 1.3.6.1.4.1.1332.1.1.5.3.3.7.2.1;

        leaf msanL2cpProtocolName {
          type rfc1213-mib:DisplayString {
            length "1..32";
          }
          description
           "L2CP protocol name";
          smiv2:max-access not-accessible;
          smiv2:oid 1.3.6.1.4.1.1332.1.1.5.3.3.7.2.1.1;
        }

        leaf msanL2cpProtocolMacDestAddr {
          type yang:mac-address;
          description
           "MAC destination address of L2CP protocol.
            Empty string indicates that protocol is related to any MAC address.";
          smiv2:defval "";
          smiv2:max-access read-write;
          smiv2:oid 1.3.6.1.4.1.1332.1.1.5.3.3.7.2.1.2;
        }

        leaf msanL2cpProtocolEthertype {
          type int32 {
            range "0..65535";
          }
          description
           "L2CP protocol Ethertype.
            A value of 65535 indicates that parameter has not been defined.";
          smiv2:defval 65535;
          smiv2:max-access read-write;
          smiv2:oid 1.3.6.1.4.1.1332.1.1.5.3.3.7.2.1.3;
        }

        leaf msanL2cpProtocolSubtype {
          type int32 {
                        range "0..255";
                    }

          description
           "L2CP protocol subtype.
            A value of 255 indicates that parameter has not been defined.";
          smiv2:defval 255;
          smiv2:max-access read-write;
          smiv2:oid 1.3.6.1.4.1.1332.1.1.5.3.3.7.2.1.4;
        }
      }
    }

    container msanL2cpProfileProtocolTable {
      description
       "Table with connection between profiles and protocols";
      smiv2:oid 1.3.6.1.4.1.1332.1.1.5.3.3.7.3;

      list msanL2cpProfileProtocolEntry {
        key "msanL2cpProfileName msanL2cpProtocolName";
        description
         "Description.";
        smiv2:oid 1.3.6.1.4.1.1332.1.1.5.3.3.7.3.1;

        leaf msanL2cpProfileName {
          type leafref {
            path "/iskratel-msan:ISKRATEL-MSAN-MIB/iskratel-msan:msanL2cpProfileTable/iskratel-msan:msanL2cpProfileEntry/iskratel-msan:msanL2cpProfileName";
          }
        }

        leaf msanL2cpProtocolName {
          type leafref {
            path "/iskratel-msan:ISKRATEL-MSAN-MIB/iskratel-msan:msanL2cpProtocolTable/iskratel-msan:msanL2cpProtocolEntry/iskratel-msan:msanL2cpProtocolName";
          }
        }

        leaf msanL2cpProfileProtocolRule {
          type enumeration {
            enum discard {
              value 1;
            }
            enum peer {
              value 2;
            }
            enum tunnel {
              value 3;
            }
          }
          description
           "L2CP protocol rule.";
          smiv2:max-access read-write;
          smiv2:oid 1.3.6.1.4.1.1332.1.1.5.3.3.7.3.1.1;
        }
      }
    }

    container msanL2cpProfileVlanTable {
      description
       "Table is used for connecting l2cp profile with vlan_id.";
      smiv2:oid 1.3.6.1.4.1.1332.1.1.5.3.3.7.4;

      list msanL2cpProfileVlanEntry {
        key "msanL2cpProfileName dot1qVlanIndex";
        description
         "Description.";
        smiv2:oid 1.3.6.1.4.1.1332.1.1.5.3.3.7.4.1;

        leaf msanL2cpProfileName {
          type leafref {
            path "/iskratel-msan:ISKRATEL-MSAN-MIB/iskratel-msan:msanL2cpProfileTable/iskratel-msan:msanL2cpProfileEntry/iskratel-msan:msanL2cpProfileName";
          }
        }

        leaf dot1qVlanIndex {
          type leafref {
            path "/q-bridge:Q-BRIDGE-MIB/q-bridge:dot1qVlanCurrentTable/q-bridge:dot1qVlanCurrentEntry/q-bridge:dot1qVlanIndex";
          }
        }
      }
    }

    container msanOnuFlowProfileTable {
      description
       "Description.";
      smiv2:oid 1.3.6.1.4.1.1332.1.1.5.3.3.20.1;

      list msanOnuFlowProfileEntry {
        key msanOnuFlowProfileName;
        description
         "Description.";
        smiv2:oid 1.3.6.1.4.1.1332.1.1.5.3.3.20.1.1;

        leaf msanOnuFlowProfileName {
          type rfc1213-mib:DisplayString {
            length "0..64";
          }
          description
           "ONU Flow Profile Name.";
          smiv2:max-access not-accessible;
          smiv2:oid 1.3.6.1.4.1.1332.1.1.5.3.3.20.1.1.1;
        }

        leaf msanOnuFlowProfileMatchUsCVlanIdRange {
          type binary {
            length "0..512";
          }
          description
           "Match ONU upstream packet frame with specified list (bitmask) of Customer VLAN Id.
            An empty string indicates that parameter has not been defined.";
          smiv2:defval "";
          smiv2:max-access read-write;
          smiv2:oid 1.3.6.1.4.1.1332.1.1.5.3.3.20.1.1.10;
        }

        leaf msanOnuFlowProfileMatchUsCPcp {
          type int32;
          description
           "Match ONU upstream packet frame with specified Customer PCP (Priority Code Point) -
            PCP is also known as class of service (CoS) bits.
            A value of -1 indicates that parameter has not been defined.";
          smiv2:defval -1;
          smiv2:max-access read-write;
          smiv2:oid 1.3.6.1.4.1.1332.1.1.5.3.3.20.1.1.11;
        }

        leaf msanOnuFlowProfileUsCdr {
          type int32 {
            range "128..2500000";
          }
          units kbps;
          description
           "ONU upstream committed data rate (E-CDR) in kbps.
            Any rate value can be entered, but is rounded up to the multiple of 64 kbps.
            
            Limitation: Commited rate cannot be higher than peak rate.";
          smiv2:max-access read-write;
          smiv2:oid 1.3.6.1.4.1.1332.1.1.5.3.3.20.1.1.12;
        }

        leaf msanOnuFlowProfileUsPdr {
          type int32 {
            range "128..2500000";
          }
          units kbps;
          description
           "ONU upstream peak data rate (E-PDR) in kbps.
            Any rate value can be entered, but is rounded up to the multiple of 64 kbps.
            
            Limitation: Peak rate cannot be lower than guaranteed rate.";
          smiv2:max-access read-write;
          smiv2:oid 1.3.6.1.4.1.1332.1.1.5.3.3.20.1.1.13;
        }

        leaf msanOnuFlowProfileUsFlowPriority {
          type int32 {
            range "0..7";
          }
          description
           "ONU upstream flow priority .";
          smiv2:max-access read-write;
          smiv2:oid 1.3.6.1.4.1.1332.1.1.5.3.3.20.1.1.14;
        }

        leaf msanOnuFlowProfileDsFlowPriority {
          type int32 {
            range "0..7";
          }
          description
           "ONU downstream flow priority .";
          smiv2:max-access read-write;
          smiv2:oid 1.3.6.1.4.1.1332.1.1.5.3.3.20.1.1.15;
        }
                leaf msanOnuFlowProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanOnuVlanProfileTable {
      description
       "description";
      smiv2:oid 1.3.6.1.4.1.1332.1.1.5.3.3.21.1;

      list msanOnuVlanProfileEntry {
        key msanOnuVlanProfileName;
        description
         "Row Description";
        smiv2:oid 1.3.6.1.4.1.1332.1.1.5.3.3.21.1.1;

        leaf msanOnuVlanProfileName {
          type rfc1213-mib:DisplayString {
            length "1..64";
          }
          description
           "ONU Vlan Profile Name.";
          smiv2:max-access not-accessible;
          smiv2:oid 1.3.6.1.4.1.1332.1.1.5.3.3.21.1.1.1;
        }

        leaf msanOnuVlanProfileDownstreamMode {
          type enumeration {
            enum enable {
              value 1;
            }
            enum disable {
              value 2;
            }
          }
          description
           "Enable maping in downstream direction also.
            
            When enabled, downstream tagging operation is performed
            in inverse order of that in upstream direction.
            
            When disabled, all downstream frames are forwarded unmodified.";
          smiv2:defval enable;
          smiv2:max-access read-write;
          smiv2:oid 1.3.6.1.4.1.1332.1.1.5.3.3.21.1.1.2;
        }

        leaf msanOnuVlanProfileInputTPID {
          type uint32;
          description
           "Input TPID (Tag Protocol Identifier).
            Default value is 0x8100.";
          smiv2:defval 33024;
          smiv2:max-access read-write;
          smiv2:oid 1.3.6.1.4.1.1332.1.1.5.3.3.21.1.1.3;
        }

        leaf msanOnuVlanProfileOutputTPID {
          type uint32;
          description
           "Output TPID (Tag Protocol Identifier).
            Default value is 0x88A8.";
          smiv2:defval 34984;
          smiv2:max-access read-write;
          smiv2:oid 1.3.6.1.4.1.1332.1.1.5.3.3.21.1.1.4;
        }
                leaf msanOnuVlanProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanOnuVlanProfileRuleTable {
      description
       "description";
      smiv2:oid 1.3.6.1.4.1.1332.1.1.5.3.3.21.2;

      list msanOnuVlanProfileRuleEntry {
        key "msanOnuVlanProfileName msanOnuVlanProfileRuleId";
        description
         "Row Description";
        smiv2:oid 1.3.6.1.4.1.1332.1.1.5.3.3.21.2.1;

        leaf msanOnuVlanProfileName {
          type leafref {
            path "/iskratel-msan:ISKRATEL-MSAN-MIB/iskratel-msan:msanOnuVlanProfileTable/iskratel-msan:msanOnuVlanProfileEntry/iskratel-msan:msanOnuVlanProfileName";
          }
        }

        leaf msanOnuVlanProfileRuleId {
          type int32;
          description
           "ONU Vlan Rule Index.";
          smiv2:max-access not-accessible;
          smiv2:oid 1.3.6.1.4.1.1332.1.1.5.3.3.21.2.1.1;
        }

        leaf msanOnuVlanProfileRuleMatchSVlanId {
          type int32 {
            range "-1..4096";
          }
          description
           "Match frames with selected S-VLAN (outer) ID:
            0 .. 4094  Match received frames with this S-VLAN ID.
            4096 Match received frames without S-TAG.
            -1  Do not match by S-VLAN ID (Default).";
          smiv2:defval 4096;
          smiv2:max-access read-write;
          smiv2:oid 1.3.6.1.4.1.1332.1.1.5.3.3.21.2.1.4;
        }

        leaf msanOnuVlanProfileRuleMatchSPcp {
          type int32 {
            range "-1..7";
          }
          description
           "Match frames with selected S-PCP (outer) value:
            0..7 Match received frames on this S-PCP priority (P bit) value.
            -1 Do not match on S-PCP (default).";
          smiv2:defval -1;
          smiv2:max-access read-write;
          smiv2:oid 1.3.6.1.4.1.1332.1.1.5.3.3.21.2.1.5;
        }

        leaf msanOnuVlanProfileRuleMatchSTPID {
          type enumeration {
            enum do-not-match {
              value 0;
            }
            enum match-value-8100 {
              value 1;
            }
            enum match-input-tpid {
              value 2;
            }
          }
          description
           "Match frames with selected S-TPID (outer):
            0 do not match on S-TPID
            1 match on S-TPID value 0x8100
            2 match on value of parameter msanOnuVlanProfileInputTPID";
          smiv2:defval do-not-match;
          smiv2:max-access read-write;
          smiv2:oid 1.3.6.1.4.1.1332.1.1.5.3.3.21.2.1.6;
        }

        leaf msanOnuVlanProfileRuleMatchCVlanId {
          type int32 {
            range "-1..4096";
          }
          description
           "Match frames with selected C-VLAN (inner) ID:
            0 .. 4094  Match received frames with this C-VLAN ID.
            4096 Match received frames without C-TAG.
            -1  Do not match by C-VLAN ID (Default).";
          smiv2:defval 4096;
          smiv2:max-access read-write;
          smiv2:oid 1.3.6.1.4.1.1332.1.1.5.3.3.21.2.1.7;
        }

        leaf msanOnuVlanProfileRuleMatchCPcp {
          type int32;
          description
           "Match frames with selected C-PCP (inner) value:
            0..7 Match received frames on this C-PCP priority (P bit) value.
            -1 Do not match on C-PCP (default).";
          smiv2:max-access read-write;
          smiv2:oid 1.3.6.1.4.1.1332.1.1.5.3.3.21.2.1.8;
        }

        leaf msanOnuVlanProfileRuleMatchCTPID {
          type enumeration {
            enum do-not-match {
              value 0;
            }
            enum match-value-8100 {
              value 1;
            }
            enum match-input-tpid {
              value 2;
            }
          }
          description
           "Match frames with selected C-TPID (inner):
            0 do not match on C-TPID
            1 match on C-TPID value 0x8100
            2 match on value of parameter msanOnuVlanProfileInputTPID";
          smiv2:defval do-not-match;
          smiv2:max-access read-write;
          smiv2:oid 1.3.6.1.4.1.1332.1.1.5.3.3.21.2.1.9;
        }

        leaf msanOnuVlanProfileRuleMatchEthertype {
          type enumeration {
            enum do-not-match {
              value 0;
            }
            enum ipoe {
              value 1;
            }
            enum pppoe {
              value 2;
            }
            enum arp {
              value 3;
            }
            enum ipv6 {
              value 4;
            }
          }
          description
           "Match frames with selected Ethertype value.
            Standard values:
            IPoE(1)   0x0800
            PPPoE(2)  0x8863 or 0x8864
            ARP(3)   0x0806
            IPv6(4)   0x86DD
            
             A value 0 indicates that parameter is not used for match criteria.";
          smiv2:defval do-not-match;
          smiv2:max-access read-write;
          smiv2:oid 1.3.6.1.4.1.1332.1.1.5.3.3.21.2.1.11;
        }

        leaf msanOnuVlanProfileRuleRemoveTags {
          type enumeration {
            enum do-not-remove {
              value 1;
            }
            enum remove-outer {
              value 2;
            }
            enum remove-both {
              value 3;
            }
            enum discard-frame {
              value 4;
            }
          }
          description
           "VLAN tags to remove.";
          smiv2:defval do-not-remove;
          smiv2:max-access read-write;
          smiv2:oid 1.3.6.1.4.1.1332.1.1.5.3.3.21.2.1.12;
        }

        leaf msanOnuVlanProfileRuleAddSTag {
          type enumeration {
            enum enable {
              value 1;
            }
            enum disable {
              value 2;
            }
          }
          description
           "Add a S-TAG.";
          smiv2:defval disable;
          smiv2:max-access read-write;
          smiv2:oid 1.3.6.1.4.1.1332.1.1.5.3.3.21.2.1.13;
        }

        leaf msanOnuVlanProfileRuleAddSPcp {
          type int32 {
            range "0..10";
          }
          description
           "Set priority in added S-TAG:
            0..7 insert this priority value to the S-TAG
            8 copy the C-TAG priority value of the received frame.
            9 copy the S-TAG priority value of the received frame.
            10 copy the DSCP value of the received frame.";
          smiv2:defval 0;
          smiv2:max-access read-write;
          smiv2:oid 1.3.6.1.4.1.1332.1.1.5.3.3.21.2.1.14;
        }

        leaf msanOnuVlanProfileRuleAddSVlanId {
          type int32 {
            range "0..4097";
          }
          description
           "Set VID in added S-TAG:
            000..4094 Use this value as the VID in the added S-TAG.
            4096 copy the C-VID value of the received frame.
            4097 copy the S-VID value of the received frame.";
          smiv2:defval 0;
          smiv2:max-access read-write;
          smiv2:oid 1.3.6.1.4.1.1332.1.1.5.3.3.21.2.1.15;
        }

        leaf msanOnuVlanProfileRuleAddSTPID {
          type enumeration {
            enum set-value-0x8100 {
              value 1;
            }
            enum use-output-tpid {
              value 2;
            }
            enum copy-c-tpid {
              value 3;
            }
            enum copy-s-tpid {
              value 4;
            }
          }
          description
           "Set TPID in added S-TAG:
            0 do not change (use default value)
            1 set to value 0x8100
            2 copy the value of parameter msanOnuVlanProfileOutputTPID
            3 copy the C-TPID value of the received frame.
            4 copy the S-TPID value of the received frame.";
          smiv2:defval copy-c-tpid;
          smiv2:max-access read-write;
          smiv2:oid 1.3.6.1.4.1.1332.1.1.5.3.3.21.2.1.16;
        }

        leaf msanOnuVlanProfileRuleAddCTag {
          type enumeration {
            enum enable {
              value 1;
            }
            enum disable {
              value 2;
            }
          }
          description
           "Add a S-TAG.";
          smiv2:defval disable;
          smiv2:max-access read-write;
          smiv2:oid 1.3.6.1.4.1.1332.1.1.5.3.3.21.2.1.17;
        }

        leaf msanOnuVlanProfileRuleAddCPcp {
          type int32 {
            range "0..10";
          }
          description
           "Set priority in added C-TAG:
            0..7 insert this priority value to the C-TAG
            8 copy the C-TAG priority value of the received frame.
            9 copy the S-TAG priority value of the received frame.
            10 copy the DSCP value of the received frame.";
          smiv2:defval 0;
          smiv2:max-access read-write;
          smiv2:oid 1.3.6.1.4.1.1332.1.1.5.3.3.21.2.1.18;
        }

        leaf msanOnuVlanProfileRuleAddCVlanId {
          type int32 {
            range "0..4097";
          }
          description
           "Set VID in added C-TAG:
            000..4094 Use this value as the VID in the added C-TAG.
            4096 copy the C-VID value of the received frame.
            4097 copy the S-VID value of the received frame.";
          smiv2:defval 0;
          smiv2:max-access read-write;
          smiv2:oid 1.3.6.1.4.1.1332.1.1.5.3.3.21.2.1.19;
        }

        leaf msanOnuVlanProfileRuleAddCTPID {
          type enumeration {
            enum set-value-0x8100 {
              value 1;
            }
            enum use-output-tpid {
              value 2;
            }
            enum copy-c-tpid {
              value 3;
            }
            enum copy-s-tpid {
              value 4;
            }
          }
          description
           "Set TPID in added S-TAG:
            0 do not change (use default value)
            1 set to value 0x8100
            2 copy the value of parameter msanOnuVlanProfileOutputTPID
            3 copy the C-TPID value of the received frame.
            4 copy the S-TPID value of the received frame.";
          smiv2:defval copy-c-tpid;
          smiv2:max-access read-write;
          smiv2:oid 1.3.6.1.4.1.1332.1.1.5.3.3.21.2.1.20;
        }
      }
    }

    container msanOnuMulticastProfileTable {
      description
       "Description.";
      smiv2:oid 1.3.6.1.4.1.1332.1.1.5.3.3.22.1;

      list msanOnuMulticastProfileEntry {
        key msanOnuMulticastProfileName;
        description
         "Description.";
        smiv2:oid 1.3.6.1.4.1.1332.1.1.5.3.3.22.1.1;

        leaf msanOnuMulticastProfileName {
          type rfc1213-mib:DisplayString {
            length "1..64";
          }
          description
           "ONU Multicast Profile Name.";
          smiv2:max-access not-accessible;
          smiv2:oid 1.3.6.1.4.1.1332.1.1.5.3.3.22.1.1.1;
        }

        leaf msanOnuMulticastProfileIgmpMode {
          type enumeration {
            enum flooding {
              value 1;
            }
            enum snooping {
              value 2;
            }
          }
          description
           "ONU IGMP Mode.";
          smiv2:defval flooding;
          smiv2:max-access read-write;
          smiv2:oid 1.3.6.1.4.1.1332.1.1.5.3.3.22.1.1.10;
        }

        leaf msanOnuMulticastProfileIgmpProxy {
          type enumeration {
            enum enable {
              value 1;
            }
            enum disable {
              value 2;
            }
          }
          description
           "ONU IGMP Proxy admin state.";
          smiv2:defval disable;
          smiv2:max-access read-write;
          smiv2:oid 1.3.6.1.4.1.1332.1.1.5.3.3.22.1.1.11;
        }

        leaf msanOnuMulticastProfileIgmpSnoopingFastLeave {
          type enumeration {
            enum enable {
              value 1;
            }
            enum disable {
              value 2;
            }
          }
          description
           "ONU IGMP Snooping Fast Leave admin state.";
          smiv2:defval enable;
          smiv2:max-access read-write;
          smiv2:oid 1.3.6.1.4.1.1332.1.1.5.3.3.22.1.1.12;
        }

        leaf msanOnuMulticastProfileUsIgmpTciVlanId {
          type int32 {
            range "0..4094";
          }
          description
           "ONU Upstream IGMP TCI (Tag Control Information) VLAN ID.
            
            Value 0 means that parameter is not defined.";
          smiv2:max-access read-write;
          smiv2:oid 1.3.6.1.4.1.1332.1.1.5.3.3.22.1.1.13;
        }

        leaf msanOnuMulticastProfileUsIgmpTciPcpValue {
          type int32 {
            range "-1..7";
          }
          description
           "ONU Upstream IGMP TCI (Tag Control Information) PCP (Priority Code Point) value (0-7) = CoS.";
          smiv2:defval 0;
          smiv2:max-access read-write;
          smiv2:oid 1.3.6.1.4.1.1332.1.1.5.3.3.22.1.1.14;
        }

        leaf msanOnuMulticastProfileUsIgmpTciCtrlMode {
          type enumeration {
            enum transparent {
              value 1;
            }
            enum add {
              value 2;
            }
            enum replace {
              value 3;
            }
            enum replace-vid-only {
              value 4;
            }
            enum smart {
              value 5;
            }
          }
          description
           "ONU Upstream IGMP TCI (Tag Control Information) Control mode.";
          smiv2:defval smart;
          smiv2:max-access read-write;
          smiv2:oid 1.3.6.1.4.1.1332.1.1.5.3.3.22.1.1.15;
        }

        leaf msanOnuMulticastProfileDsVlanTagging {
          type enumeration {
            enum enable {
              value 1;
            }
            enum disable {
              value 2;
            }
          }
          description
           "ONU Downstream tagging of multicast traffic.";
          smiv2:max-access read-write;
          smiv2:oid 1.3.6.1.4.1.1332.1.1.5.3.3.22.1.1.16;
        }

        leaf msanOnuMulticastProfileDsGemPort {
          type int32 {
            range "3800..4000";
          }
          description
           "Downstream multicast GEM port number.
            Standard values are 3800 - 3999.
            Default value is 4000 (Undefined).";
          smiv2:defval 4000;
          smiv2:max-access read-write;
          smiv2:oid 1.3.6.1.4.1.1332.1.1.5.3.3.22.1.1.17;
        }
                leaf msanOnuMulticastProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanOnuTcontProfileTable {
      description
       "Description.";
      smiv2:oid 1.3.6.1.4.1.1332.1.1.5.3.3.23.1;

      list msanOnuTcontProfileEntry {
        key msanOnuTcontProfileName;
        description
         "Description.";
        smiv2:oid 1.3.6.1.4.1.1332.1.1.5.3.3.23.1.1;

        leaf msanOnuTcontProfileName {
          type rfc1213-mib:DisplayString {
            length "1..64";
          }
          description
           "ONU T-CONT Profile Name.";
          smiv2:max-access not-accessible;
          smiv2:oid 1.3.6.1.4.1.1332.1.1.5.3.3.23.1.1.1;
        }

        leaf msanOnuTcontProfileTcontId {
          type int32 {
            range "1..6";
          }
          description
           "ONU T-CONT index.";
          smiv2:defval 1;
          smiv2:max-access read-write;
          smiv2:oid 1.3.6.1.4.1.1332.1.1.5.3.3.23.1.1.10;
        }

        leaf msanOnuTcontProfileTcontType {
          type int32 {
            range "1..5";
          }
          description
           "ONU T-CONT type.";
          smiv2:defval 5;
          smiv2:max-access read-write;
          smiv2:oid 1.3.6.1.4.1.1332.1.1.5.3.3.23.1.1.11;
        }

        leaf msanOnuTcontProfileFixedDataRate {
          type int32 {
            range "128..2500000";
          }
          units kbps;
          description
           "ONU T-CONT Fixed data rate.
            Any rate value can be entered, but is rounded up to the multiple of 64 kbps.
            
            Limitation: Maximum rate cannot be lower than the sum of fixed and assured rates.";
          smiv2:defval 128;
          smiv2:max-access read-write;
          smiv2:oid 1.3.6.1.4.1.1332.1.1.5.3.3.23.1.1.12;
        }

        leaf msanOnuTcontProfileAssuredDataRate {
          type int32 {
            range "0..2500000";
          }
          units kbps;
          description
           "ONU T-CONT Assured data rate  (256 - 2500000 kbps).
            Default value is 0, meaning that no rate is configured.
            Any rate value can be entered, but is rounded up to the multiple of 64 kbps.
            
            Limitation: Maximum rate cannot be lower than the sum of fixed and assured rates.";
          smiv2:defval 0;
          smiv2:max-access read-write;
          smiv2:oid 1.3.6.1.4.1.1332.1.1.5.3.3.23.1.1.13;
        }

        leaf msanOnuTcontProfileMaxDataRate {
          type int32 {
            range "128..2500000";
          }
          units kbps;
          description
           "ONU T-CONT Maximum data rate.
            Any rate value can be entered, but is rounded up to the multiple of 64 kbps.
            
            Limitation: Maximum rate cannot be lower than the sum of fixed and assured rates";
          smiv2:defval 1024;
          smiv2:max-access read-write;
          smiv2:oid 1.3.6.1.4.1.1332.1.1.5.3.3.23.1.1.14;
        }
                leaf msanOnuTcontProfileUsage {
                    type enumeration {
                        enum attached {
                            value 1;
                        }
                        enum notAttached {
                            value 2;
                        }
                    }
                    config false;
                    status current;
                    description 
                        "Profile usage.
                         If profile is attached,  profile values can't be edited.
                         ";
                }

      }
    }

    container msanProfilePortDataTable {
      description
       "Description.";
      smiv2:oid 1.3.6.1.4.1.1332.1.1.5.3.3.50;

      list msanProfilePortDataEntry {
        key ifName;
        description
         "Description.";
        smiv2:oid 1.3.6.1.4.1.1332.1.1.5.3.3.50.1;

        leaf ifName {
          type if:interface-ref;
          description 
           "A reference to the name of a configured network layer
            interface.";
        }

        leaf msanProfilePortDataCVid {
          type int32 {
            range "-1..4094";
          }
          description
           "Nativ C-VLAN Id.
            A value of -1 indicates that parameter has not been defined.";
          smiv2:defval -1;
          smiv2:max-access read-write;
          smiv2:oid 1.3.6.1.4.1.1332.1.1.5.3.3.50.1.1;
        }

        leaf msanProfilePortDataSVid {
          type int32 {
            range "-1..4094";
          }
          description
           "S-VLAN Id.
            A value of -1 indicates that parameter has not been defined.";
          smiv2:defval -1;
          smiv2:max-access read-write;
          smiv2:oid 1.3.6.1.4.1.1332.1.1.5.3.3.50.1.2;
        }
      }
    }

    container msanDhcpRaPortConfigTable {
      description
       "Table od DHCP RA parameters per port.";
      smiv2:oid 1.3.6.1.4.1.1332.1.1.5.3.4.2;

      list msanDhcpRaPortConfigEntry {
        key ifIndex;
        description
         "Description.";
        smiv2:oid 1.3.6.1.4.1.1332.1.1.5.3.4.2.1;

        leaf ifIndex {
          type leafref {
            path "/if-mib:interfaces/if-mib:ifEntry/if-mib:ifIndex";
          }
        }

        leaf msanDhcpRaPortState {
          type enumeration {
            enum enable {
              value 1;
            }
            enum enableCli {
              value 2;
            }
            enum enableSrv {
              value 3;
            }
            enum disable {
              value 4;
            }
          }
          description
           "State of DHCP Relay Agent on the port (enable, disable, enable-client, enable-server) ";
          smiv2:max-access read-write;
          smiv2:oid 1.3.6.1.4.1.1332.1.1.5.3.4.2.1.1;
        }

        leaf msanDhcpRaPortCircuitId {
          type binary;
          description
           "Option 82 Circuit Id for the port.";
          smiv2:max-access read-only;
          smiv2:oid 1.3.6.1.4.1.1332.1.1.5.3.4.2.1.2;
        }

        leaf msanDhcpRaPortRemoteId {
          type binary;
          description
           "Option 82 Remote Id for the port.";
          smiv2:max-access read-write;
          smiv2:oid 1.3.6.1.4.1.1332.1.1.5.3.4.2.1.3;
        }

        leaf msanDhcpRaPortMeter {
          type enumeration {
            enum enable {
              value 1;
            }
            enum disable {
              value 2;
            }
          }
          description
           "Enable or disable DHCP metering on port.";
          smiv2:max-access read-write;
          smiv2:oid 1.3.6.1.4.1.1332.1.1.5.3.4.2.1.4;
        }

        leaf msanDhcpRaPortMaxDataRate {
          type int32;
          units kb/s;
          description
           "Allowed throughput of incoming DHCP traffic on a port (kb/s)";
          smiv2:max-access read-write;
          smiv2:oid 1.3.6.1.4.1.1332.1.1.5.3.4.2.1.5;
        }

        leaf msanDhcpRaPortCircuitType {
          type enumeration {
            enum trusted {
              value 1;
            }
            enum untrusted {
              value 2;
            }
            enum notConfigured {
              value 3;
            }
          }
          description
           "Specifies DHCP RA Circuit type per port as trusted(1) or untrusted(2).";
          smiv2:defval notConfigured;
          smiv2:max-access read-write;
          smiv2:oid 1.3.6.1.4.1.1332.1.1.5.3.4.2.1.6;
        }

        leaf msanDhcpRaPortOpt82 {
          type enumeration {
            enum enable {
              value 1;
            }
            enum disable {
              value 2;
            }
            enum notConfigured {
              value 3;
            }
          }
          description
           "Specifies DHCP Relay Agent option 82 insertion status per port.";
          smiv2:defval notConfigured;
          smiv2:max-access read-write;
          smiv2:oid 1.3.6.1.4.1.1332.1.1.5.3.4.2.1.7;
        }

        leaf msanDhcpRaPortOpt82ReplyMode {
          type enumeration {
            enum keep {
              value 1;
            }
            enum remove {
              value 2;
            }
            enum notConfigured {
              value 3;
            }
          }
          description
           "Specifies DHCP Relay Agent keep/remove option 82 in replies per port.";
          smiv2:defval notConfigured;
          smiv2:max-access read-write;
          smiv2:oid 1.3.6.1.4.1.1332.1.1.5.3.4.2.1.8;
        }

        leaf msanDhcpRaPortOpt82UnicastExtStatus {
          type enumeration {
            enum enable {
              value 1;
            }
            enum disable {
              value 2;
            }
            enum notConfigured {
              value 3;
            }
          }
          description
           "The desired state of insertion of option 82 in unicast frames per port.";
          smiv2:defval notConfigured;
          smiv2:max-access read-write;
          smiv2:oid 1.3.6.1.4.1.1332.1.1.5.3.4.2.1.9;
        }

        leaf msanDhcpRaPortCircuitIdType {
          type enumeration {
            enum iskratel {
              value 1;
            }
            enum standard {
              value 2;
            }
            enum atm {
              value 3;
            }
          }
          description
           "Circuit Id syntax mode per port.";
          smiv2:defval iskratel;
          smiv2:max-access read-write;
          smiv2:oid 1.3.6.1.4.1.1332.1.1.5.3.4.2.1.10;
        }
      }
    }

    container msanDhcpRaFullModeVlanTable {
      description
       "Description.";
      smiv2:oid 1.3.6.1.4.1.1332.1.1.5.3.4.3;

      list msanDhcpRaFullModeVlanEntry {
        key "msanDhcpRaFullModeVlanId msanDhcpRaFullModeVlanSrvIpAddr";
        description
         "Description.";
        smiv2:oid 1.3.6.1.4.1.1332.1.1.5.3.4.3.1;

        leaf msanDhcpRaFullModeVlanId {
          type int32 {
            range "1..4094";
          }
          description
           "The VLAN identifier (refers to dot1qVlanIndex) where DHCP Client resides.";
          smiv2:max-access not-accessible;
          smiv2:oid 1.3.6.1.4.1.1332.1.1.5.3.4.3.1.1;
        }

        leaf msanDhcpRaFullModeVlanSrvIpAddr {
          type inet:ipv4-address;
          description
           "The IP address of DHCP Server for specified VLAN.";
          smiv2:max-access not-accessible;
          smiv2:oid 1.3.6.1.4.1.1332.1.1.5.3.4.3.1.2;
        }

        leaf msanDhcpRaFullModeVlanRowStatus {
          type snmpv2-tc:RowStatus;
          description
           "The row status object controls the creation/deletion of rows in this table. Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.4.3.1.3;
        }
      }
    }

    container msanDhcpRaStatTable {
      description
       "Description.";
      smiv2:oid 1.3.6.1.4.1.1332.1.1.5.3.4.5;

      list msanDhcpRaStatEntry {
        key ifIndex;
        description
         "Description.";
        smiv2:oid 1.3.6.1.4.1.1332.1.1.5.3.4.5.1;

        leaf ifIndex {
          type leafref {
            path "/if-mib:interfaces/if-mib:ifEntry/if-mib:ifIndex";
          }
        }

        leaf msanDhcpRaStatDiscover {
          type yang:counter32;
          description
           "Number of received DHCP DISCOVER packets.";
          smiv2:max-access read-only;
          smiv2:oid 1.3.6.1.4.1.1332.1.1.5.3.4.5.1.1;
        }

        leaf msanDhcpRaStatRequest {
          type yang:counter32;
          description
           "Number of received DHCP REQUEST packets.";
          smiv2:max-access read-only;
          smiv2:oid 1.3.6.1.4.1.1332.1.1.5.3.4.5.1.2;
        }

        leaf msanDhcpRaStatOffer {
          type yang:counter32;
          description
           "Number of received DHCP OFFER packets.";
          smiv2:max-access read-only;
          smiv2:oid 1.3.6.1.4.1.1332.1.1.5.3.4.5.1.3;
        }

        leaf msanDhcpRaStatACK {
          type yang:counter32;
          description
           "Number of received DHCP ACKNOWLAGE (ACK) packets.";
          smiv2:max-access read-only;
          smiv2:oid 1.3.6.1.4.1.1332.1.1.5.3.4.5.1.4;
        }

        leaf msanDhcpRaStatNAK {
          type yang:counter32;
          description
           "Number of received DHCP NOT ACKNOWLAGE (NAK) packets.";
          smiv2:max-access read-only;
          smiv2:oid 1.3.6.1.4.1.1332.1.1.5.3.4.5.1.5;
        }

        leaf msanDhcpRaStatDecline {
          type yang:counter32;
          description
           "Number of received DHCP DECLINE packets.";
          smiv2:max-access read-only;
          smiv2:oid 1.3.6.1.4.1.1332.1.1.5.3.4.5.1.6;
        }

        leaf msanDhcpRaStatMaxPacketSizeExceeded {
          type yang:counter32;
          description
           "Number of received DHCP packets with max. packet size exceeded. ";
          smiv2:max-access read-only;
          smiv2:oid 1.3.6.1.4.1.1332.1.1.5.3.4.5.1.7;
        }

        leaf msanDhcpRaStatFrameErr {
          type yang:counter32;
          description
           "Number of received DHCP packets with errors in frames. ";
          smiv2:max-access read-only;
          smiv2:oid 1.3.6.1.4.1.1332.1.1.5.3.4.5.1.8;
        }

        leaf msanDhcpRaStatOpt82Present {
          type yang:counter32;
          description
           "Number of received DHCP packets with Option 82 or giaddr present. ";
          smiv2:max-access read-only;
          smiv2:oid 1.3.6.1.4.1.1332.1.1.5.3.4.5.1.9;
        }

        leaf msanDhcpRaStatFrameUnsync {
          type yang:counter32;
          description
           "Number of received packets with frames not synchronized with state machines.";
          smiv2:max-access read-only;
          smiv2:oid 1.3.6.1.4.1.1332.1.1.5.3.4.5.1.10;
        }

        leaf msanDhcpRaStatRelease {
          type yang:counter32;
          description
           "Number of received DHCP RELEASE packets.";
          smiv2:max-access read-only;
          smiv2:oid 1.3.6.1.4.1.1332.1.1.5.3.4.5.1.11;
        }

        leaf msanDhcpRaStatInform {
          type yang:counter32;
          description
           "Number of received DHCP INFORM packets.";
          smiv2:max-access read-only;
          smiv2:oid 1.3.6.1.4.1.1332.1.1.5.3.4.5.1.12;
        }
      }
    }

    container msanDhcpRaVlanConfigTable {
      description
       "Table od DHCP RA parameters per Vlan.";
      smiv2:oid 1.3.6.1.4.1.1332.1.1.5.3.4.6;

      list msanDhcpRaVlanConfigEntry {
        key dot1qVlanIndex;
        description
         "Description.";
        smiv2:oid 1.3.6.1.4.1.1332.1.1.5.3.4.6.1;

        leaf dot1qVlanIndex {
          type leafref {
            path "/q-bridge:Q-BRIDGE-MIB/q-bridge:dot1qVlanCurrentTable/q-bridge:dot1qVlanCurrentEntry/q-bridge:dot1qVlanIndex";
          }
        }

        leaf msanDhcpRaVlanState {
          type enumeration {
            enum disable {
              value 1;
            }
            enum notConfigured {
              value 2;
            }
          }
          description
           "DHCP RA state for specified VLAN ID. Value notConfigured(2) means, that
            global setting is used(msanDhcpRaStatus).";
          smiv2:defval notConfigured;
          smiv2:max-access read-write;
          smiv2:oid 1.3.6.1.4.1.1332.1.1.5.3.4.6.1.1;
        }

        leaf msanDhcpRaVlanMode {
          type enumeration {
            enum full {
              value 1;
            }
            enum simplified {
              value 2;
            }
            enum notConfigured {
              value 3;
            }
          }
          description
           "DHCP RA mode for specified VLAN ID. Value notConfigured(1) means, that
            global setting is used(msanDhcpRaMode).";
          smiv2:defval notConfigured;
          smiv2:max-access read-write;
          smiv2:oid 1.3.6.1.4.1.1332.1.1.5.3.4.6.1.2;
        }

        leaf msanDhcpRaVlanOpt82 {
          type enumeration {
            enum enable {
              value 1;
            }
            enum disable {
              value 2;
            }
            enum notConfigured {
              value 3;
            }
          }
          description
           "Specifies DHCP Relay Agent option 82 insertion status per vlan.";
          smiv2:defval notConfigured;
          smiv2:max-access read-write;
          smiv2:oid 1.3.6.1.4.1.1332.1.1.5.3.4.6.1.3;
        }

        leaf msanDhcpRaVlanOpt82ReplyMode {
          type enumeration {
            enum keep {
              value 1;
            }
            enum remove {
              value 2;
            }
            enum notConfigured {
              value 3;
            }
          }
          description
           "Specifies DHCP Relay Agent keep/remove option 82 in replies per vlan.";
          smiv2:defval notConfigured;
          smiv2:max-access read-write;
          smiv2:oid 1.3.6.1.4.1.1332.1.1.5.3.4.6.1.4;
        }

        leaf msanDhcpRaVlanOpt82UnicastExtStatus {
          type enumeration {
            enum enable {
              value 1;
            }
            enum disable {
              value 2;
            }
            enum notConfigured {
              value 3;
            }
          }
          description
           "The desired state of insertion of option 82 in unicast frames per vlan.";
          smiv2:defval notConfigured;
          smiv2:max-access read-write;
          smiv2:oid 1.3.6.1.4.1.1332.1.1.5.3.4.6.1.5;
        }

        leaf msanDhcpRaVlanCircuitIdType {
          type enumeration {
            enum iskratel {
              value 1;
            }
            enum standard {
              value 2;
            }
            enum notConfigured {
              value 3;
            }
          }
          description
           "Circuit Id syntax mode per vlan.";
          smiv2:defval notConfigured;
          smiv2:max-access read-write;
          smiv2:oid 1.3.6.1.4.1.1332.1.1.5.3.4.6.1.6;
        }
      }
    }

    container msanDhcpRaPortVlanConfigTable {
      description
       "Description.";
      smiv2:oid 1.3.6.1.4.1.1332.1.1.5.3.4.7;

      list msanDhcpRaPortVlanConfigEntry {
        key "ifIndex dot1qVlanIndex";
        description
         "Description.";
        smiv2:oid 1.3.6.1.4.1.1332.1.1.5.3.4.7.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanDhcpRaPortVlanRemoteId {
          type binary;
          description
           "The VLAN identifier (refers to dot1qVlanIndex) where DHCP Client resides.";
          smiv2:defval "";
          smiv2:max-access read-write;
          smiv2:oid 1.3.6.1.4.1.1332.1.1.5.3.4.7.1.1;
        }

        leaf msanDhcpRaPortVlanConfigRowStatus {
          type snmpv2-tc:RowStatus;
          description
           "The row status object controls the creation/deletion of rows in this table.
            For row creation use createAndWait(5) [createAndGo(4) is not supported].";
          smiv2:max-access read-write;
          smiv2:oid 1.3.6.1.4.1.1332.1.1.5.3.4.7.1.2;
        }

        leaf msanDhcpRaPortVlanCircuitIdType {
          type enumeration {
            enum iskratel {
              value 1;
            }
            enum standard {
              value 2;
            }
            enum notConfigured {
              value 3;
            }
            enum custom {
              value 4;
            }
          }
          description
           "Circuit Id syntax mode per vlan per port.";
          smiv2:defval notConfigured;
          smiv2:max-access read-write;
          smiv2:oid 1.3.6.1.4.1.1332.1.1.5.3.4.7.1.3;
        }

        leaf msanDhcpRaPortVlanCircuitId {
          type rfc1213-mib:DisplayString;
          description
           "Option 82 Circuit Id per vlan per port.";
          smiv2:max-access read-only;
          smiv2:oid 1.3.6.1.4.1.1332.1.1.5.3.4.7.1.4;
        }
      }
    }

    container msanDhcpv6RaPortStatTable {
      description
       "Description.";
      smiv2:oid 1.3.6.1.4.1.1332.1.1.5.3.4.101.1;

      list msanDhcpv6RaPortStatEntry {
        key ifIndex;
        description
         "Description.";
        smiv2:oid 1.3.6.1.4.1.1332.1.1.5.3.4.101.1.1;

        leaf ifIndex {
          type leafref {
            path "/if-mib:interfaces/if-mib:ifEntry/if-mib:ifIndex";
          }
        }

        leaf msanDhcpv6PortRaStatSolicit {
          type int32;
          description
           "Number of received DHCPv6 solicit packets.";
          smiv2:max-access read-only;
          smiv2:oid 1.3.6.1.4.1.1332.1.1.5.3.4.101.1.1.1;
        }

        leaf msanDhcpv6PortRaStatAdvertise {
          type int32;
          description
           "Number of received DHCPv6 advertise packets.";
          smiv2:max-access read-only;
          smiv2:oid 1.3.6.1.4.1.1332.1.1.5.3.4.101.1.1.2;
        }

        leaf msanDhcpv6PortRaStatRequest {
          type int32;
          description
           "Number of received DHCPv6 request packets.";
          smiv2:max-access read-only;
          smiv2:oid 1.3.6.1.4.1.1332.1.1.5.3.4.101.1.1.3;
        }

        leaf msanDhcpv6PortRaStatReply {
          type int32;
          description
           "Number of received DHCPv6 reply packets.";
          smiv2:max-access read-only;
          smiv2:oid 1.3.6.1.4.1.1332.1.1.5.3.4.101.1.1.4;
        }

        leaf msanDhcpv6PortRaStatRenew {
          type int32;
          description
           "Number of received DHCPv6 renew packets.";
          smiv2:max-access read-only;
          smiv2:oid 1.3.6.1.4.1.1332.1.1.5.3.4.101.1.1.5;
        }

        leaf msanDhcpv6PortRaStatRebind {
          type int32;
          description
           "Number of received DHCPv6 rebind packets.";
          smiv2:max-access read-only;
          smiv2:oid 1.3.6.1.4.1.1332.1.1.5.3.4.101.1.1.6;
        }

        leaf msanDhcpv6PortRaStatDecline {
          type int32;
          description
           "Number of received DHCPv6 decline packets.";
          smiv2:max-access read-only;
          smiv2:oid 1.3.6.1.4.1.1332.1.1.5.3.4.101.1.1.7;
        }

        leaf msanDhcpv6PortRaStatReconfigure {
          type int32;
          description
           "Number of received DHCPv6 reconfigure packets.";
          smiv2:max-access read-only;
          smiv2:oid 1.3.6.1.4.1.1332.1.1.5.3.4.101.1.1.8;
        }

        leaf msanDhcpv6PortRaStatRelease {
          type int32;
          description
           "Number of received DHCPv6 release packets.";
          smiv2:max-access read-only;
          smiv2:oid 1.3.6.1.4.1.1332.1.1.5.3.4.101.1.1.9;
        }

        leaf msanDhcpv6PortRaStatInformRequest {
          type int32;
          description
           "Number of received DHCPv6 inform request packets.";
          smiv2:max-access read-only;
          smiv2:oid 1.3.6.1.4.1.1332.1.1.5.3.4.101.1.1.10;
        }

        leaf msanDhcpv6PortRaStatRelayForward {
          type int32;
          description
           "Number of received DHCPv6 relay forward packets.";
          smiv2:max-access read-only;
          smiv2:oid 1.3.6.1.4.1.1332.1.1.5.3.4.101.1.1.11;
        }

        leaf msanDhcpv6PortRaStatRelayReply {
          type int32;
          description
           "Number of received DHCPv6 relay reply packets.";
          smiv2:max-access read-only;
          smiv2:oid 1.3.6.1.4.1.1332.1.1.5.3.4.101.1.1.12;
        }

        leaf msanDhcpv6PortRaStatOversizeError {
          type int32;
          description
           "Number of discarded packets because max packet size exceeded.";
          smiv2:max-access read-only;
          smiv2:oid 1.3.6.1.4.1.1332.1.1.5.3.4.101.1.1.100;
        }

        leaf msanDhcpv6PortRaStatFrameError {
          type int32;
          description
           "Number of discarded packets because frame error.";
          smiv2:max-access read-only;
          smiv2:oid 1.3.6.1.4.1.1332.1.1.5.3.4.101.1.1.101;
        }

        leaf msanDhcpv6PortRaStatFrameUnsyncError {
          type int32;
          description
           "Number of received packets with frames not synchronized with state machines.";
          smiv2:max-access read-only;
          smiv2:oid 1.3.6.1.4.1.1332.1.1.5.3.4.101.1.1.102;
        }

        leaf msanDhcpv6PortRaStatSysError {
          type int32;
          description
           "Number of discarded packets because system  error.";
          smiv2:max-access read-only;
          smiv2:oid 1.3.6.1.4.1.1332.1.1.5.3.4.101.1.1.103;
        }
      }
    }

    container msanDhcpv6RaPortConfigTable {
      description
       "Table od DHCP RA parameters per port.";
      smiv2:oid 1.3.6.1.4.1.1332.1.1.5.3.4.102;

      list msanDhcpv6RaPortConfigEntry {
        key ifIndex;
        description
         "Description.";
        smiv2:oid 1.3.6.1.4.1.1332.1.1.5.3.4.102.1;

        leaf ifIndex {
          type leafref {
            path "/if-mib:interfaces/if-mib:ifEntry/if-mib:ifIndex";
          }
        }

        leaf msanDhcpv6RaPortState {
          type enumeration {
            enum enable {
              value 1;
            }
            enum enableCli {
              value 2;
            }
            enum enableSrv {
              value 3;
            }
            enum disable {
              value 4;
            }
          }
          description
           "State of DHCPv6 Relay Agent on the port (enable, disable, enable-client, enable-server) ";
          smiv2:defval enable;
          smiv2:max-access read-write;
          smiv2:oid 1.3.6.1.4.1.1332.1.1.5.3.4.102.1.1;
        }

        leaf msanDhcpv6RaPortTrusted {
          type enumeration {
            enum enable {
              value 1;
            }
            enum disable {
              value 2;
            }
          }
          description
           "Specifies DHCP RA Circuit type per port as trusted(1) or untrusted(2).
            Default value for user ports is untrusted(2) and for network ports trusted(1).";
          smiv2:max-access read-write;
          smiv2:oid 1.3.6.1.4.1.1332.1.1.5.3.4.102.1.2;
        }

        leaf msanDhcpv6RaPortInterfaceIdStandard {
          type enumeration {
            enum enable {
              value 1;
            }
            enum disable {
              value 2;
            }
          }
          description
           "DHCPv6 RA Standard Interface Id syntax mode.";
          smiv2:defval enable;
          smiv2:max-access read-write;
          smiv2:oid 1.3.6.1.4.1.1332.1.1.5.3.4.102.1.3;
        }

        leaf msanDhcpv6RaPortInterfaceId {
          type binary;
          description
           "DHCPv6 Interface Id.";
          smiv2:max-access read-only;
          smiv2:oid 1.3.6.1.4.1.1332.1.1.5.3.4.102.1.4;
        }

        leaf msanDhcpv6RaPortRemoteId {
          type binary;
          description
           "DHCPv6 Remote Id value for the port.
            If empty string, remote id is not added to DHCPv6 package.";
          smiv2:defval "";
          smiv2:max-access read-write;
          smiv2:oid 1.3.6.1.4.1.1332.1.1.5.3.4.102.1.5;
        }

        leaf msanDhcpv6RaPortRemoteIdEnterpriseNum {
          type int32 {
            range "1..999999";
          }
          description
           "DHCPv6 Remote Id enterprise number for the port.";
          smiv2:defval 1332;
          smiv2:max-access read-write;
          smiv2:oid 1.3.6.1.4.1.1332.1.1.5.3.4.102.1.6;
        }
      }
    }

    container msanDhcpv6RaVlanConfigTable {
      description
       "Table od DHCP RA parameters per Vlan.";
      smiv2:oid 1.3.6.1.4.1.1332.1.1.5.3.4.103;

      list msanDhcpv6RaVlanConfigEntry {
        key dot1qVlanIndex;
        description
         "Description.";
        smiv2:oid 1.3.6.1.4.1.1332.1.1.5.3.4.103.1;

        leaf dot1qVlanIndex {
          type leafref {
            path "/q-bridge:Q-BRIDGE-MIB/q-bridge:dot1qVlanCurrentTable/q-bridge:dot1qVlanCurrentEntry/q-bridge:dot1qVlanIndex";
          }
        }

        leaf msanDhcpv6RaVlanState {
          type enumeration {
            enum enable {
              value 1;
            }
            enum disable {
              value 2;
            }
          }
          description
           "DHCP RA state for specified VLAN ID. ";
          smiv2:defval enable;
          smiv2:max-access read-write;
          smiv2:oid 1.3.6.1.4.1.1332.1.1.5.3.4.103.1.1;
        }

        leaf msanDhcpv6RaVlanInterfaceIdStandard {
          type enumeration {
            enum enable {
              value 1;
            }
            enum disable {
              value 2;
            }
          }
          description
           "DHCPv6 RA Standard Interface Id syntax mode.";
          smiv2:defval enable;
          smiv2:max-access read-write;
          smiv2:oid 1.3.6.1.4.1.1332.1.1.5.3.4.103.1.2;
        }
      }
    }

    container msanDhcpv6RaPortVlanConfigTable {
      description
       "Description.";
      smiv2:oid 1.3.6.1.4.1.1332.1.1.5.3.4.104;

      list msanDhcpv6RaPortVlanConfigEntry {
        key "ifIndex dot1qVlanIndex";
        description
         "Description.";
        smiv2:oid 1.3.6.1.4.1.1332.1.1.5.3.4.104.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanDhcpv6RaPortVlanRemoteId {
          type binary;
          description
           "DHCPv6 Remote Id value for specified vlan_id per port.";
          smiv2:defval "";
          smiv2:max-access read-write;
          smiv2:oid 1.3.6.1.4.1.1332.1.1.5.3.4.104.1.1;
        }

        leaf msanDhcpv6RaPortVlanRemoteIdEnterpriseNum {
          type int32 {
            range "1..999999";
          }
          description
           "DHCPv6 Remote Id enterprise number for specified vlan_id per port.";
          smiv2:defval 1332;
          smiv2:max-access read-write;
          smiv2:oid 1.3.6.1.4.1.1332.1.1.5.3.4.104.1.2;
        }

        leaf msanDhcpv6RaPortVlanRowStatus {
          type snmpv2-tc:RowStatus;
          description
           "The row status object controls the creation/deletion of rows in this table.
            For row creation use createAndWait(5) [createAndGo(4) is not supported].";
          smiv2:max-access read-write;
          smiv2:oid 1.3.6.1.4.1.1332.1.1.5.3.4.104.1.3;
        }
      }
    }

    container msanIgmpSnoopingTable {
      description
       "Description.";
      smiv2:oid 1.3.6.1.4.1.1332.1.1.5.3.8.2;

      list msanIgmpSnoopingEntry {
        key ifIndex;
        description
         "Description.";
        smiv2:oid 1.3.6.1.4.1.1332.1.1.5.3.8.2.1;

        leaf ifIndex {
          type leafref {
            path "/if-mib:interfaces/if-mib:ifEntry/if-mib:ifIndex";
          }
        }

        leaf msanIgmpSnoopingIntfStandaloneQuerier {
          type int32;
          units seconds;
          description
           "Specify the period of time in seconds you want the IGMP Standalone Querier generate IGMP query packets. Value must be higher than
            msanIgmpSnoopingMaxResponseTime and lower than msanIgmpSnoopingGroupMembershipInterval or 0.
            The default is 0. A value of zero indicates that standalone querier is disabled.
            IGMP SA Querier can be activated only on one interface at the same time. ";
          smiv2:max-access read-write;
          smiv2:oid 1.3.6.1.4.1.1332.1.1.5.3.8.2.1.1;
        }

        leaf msanIgmpSnoopingIntfFilter {
          type enumeration {
            enum allowAll {
              value 0;
            }
            enum allowReports {
              value 1;
            }
            enum allowQueries {
              value 2;
            }
            enum dropAll {
              value 3;
            }
          }
          description
           "Filtering of IGMP join/leave reports or queries frames. ";
          smiv2:max-access read-write;
          smiv2:oid 1.3.6.1.4.1.1332.1.1.5.3.8.2.1.2;
        }

        leaf msanIgmpSnoopingGroupLimit {
          type int32 {
            range "0..10";
          }
          description
           "A maximum numbers of IGMP groups per interface.
            Value 0 means no limits.";
          smiv2:max-access read-write;
          smiv2:oid 1.3.6.1.4.1.1332.1.1.5.3.8.2.1.3;
        }
      }
    }

    container msanSwitchIGMPVlanCurrentMrouterTable {
      description
       "Description.";
      smiv2:oid 1.3.6.1.4.1.1332.1.1.5.3.8.3;

      list msanSwitchIGMPVlanCurrentMrouterEntry {
        key "ifIndex dot1qVlanIndex";
        description
         "Description.";
        smiv2:oid 1.3.6.1.4.1.1332.1.1.5.3.8.3.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanSwitchIGMPVlanCurrentMrouterEnableState {
          type int32;
          description
           "Returns per-interface per-vlan pairs where IGMP Mrouter is enabled. ";
          smiv2:max-access read-only;
          smiv2:oid 1.3.6.1.4.1.1332.1.1.5.3.8.3.1.1;
        }
      }
    }

    container msanSwitchIGMPSnoopingStaticIntfMulticastRouterTable {
      description
       "Description.";
      reference
       "agentSwitchIGMPSnoopingIntfTable - 1.3.6.1.4.1.6132.1.1.1.2.8.7.1";
      smiv2:oid 1.3.6.1.4.1.1332.1.1.5.3.8.4;

      list msanSwitchIGMPSnoopingStaticIntfMulticastRouterEntry {
        key ifIndex;
        description
         "Description.";
        smiv2:oid 1.3.6.1.4.1.1332.1.1.5.3.8.4.1;

        leaf ifIndex {
          type leafref {
            path "/if-mib:interfaces/if-mib:ifEntry/if-mib:ifIndex";
          }
        }

        leaf msanSwitchIGMPSnoopingIntfIndex {
          type uint32 {
            range "1..65535";
          }
          description
           "The port number to be selected. Each port maps to an interface.";
          smiv2:max-access read-only;
          smiv2:oid 1.3.6.1.4.1.1332.1.1.5.3.8.4.1.1;
        }

        leaf msanSwitchIGMPSnoopingIntfAdminMode {
          type enumeration {
            enum enable {
              value 1;
            }
            enum disable {
              value 2;
            }
          }
          status deprecated;
          description
           "This enables or disables IGMP Snooping on a selected interface.";
          smiv2:defval disable;
          smiv2:max-access read-write;
          smiv2:oid 1.3.6.1.4.1.1332.1.1.5.3.8.4.1.2;
        }

        leaf msanSwitchIGMPSnoopingIntfGroupMembershipInterval {
          type int32 {
            range "2..3600";
          }
          status deprecated;
          description
           "The amount of time in seconds that a switch will wait for a report
            from a particular group on the selected interface before deleting the
            interface from the entry. This value must be greater than
            agentSwitchIGMPSnoopingIntfMaxResponseTime.";
          smiv2:defval 260;
          smiv2:max-access read-write;
          smiv2:oid 1.3.6.1.4.1.1332.1.1.5.3.8.4.1.3;
        }

        leaf msanSwitchIGMPSnoopingIntfMaxResponseTime {
          type int32 {
            range "1..3599";
          }
          status deprecated;
          description
           "The amount of time in seconds a switch will wait after sending
            a query on the selected interface because it did not receive a report for
            a particular group in that interface.  This value must be less
            than agentSwitchIGMPSnoopingIntfGroupMembershipInterval.";
          smiv2:defval 10;
          smiv2:max-access read-write;
          smiv2:oid 1.3.6.1.4.1.1332.1.1.5.3.8.4.1.4;
        }

        leaf msanSwitchIGMPSnoopingIntfMRPExpirationTime {
          type int32 {
            range "0..3600";
          }
          status deprecated;
          description
           "The amount of time in seconds that a switch will wait for a query to be
            received on the selected interface before the interface is removed from
            the list of interfaces with multicast routers attached.";
          smiv2:defval 0;
          smiv2:max-access read-write;
          smiv2:oid 1.3.6.1.4.1.1332.1.1.5.3.8.4.1.5;
        }

        leaf msanSwitchIGMPSnoopingIntfFastLeaveAdminMode {
          type enumeration {
            enum enable {
              value 1;
            }
            enum disable {
              value 2;
            }
          }
          status deprecated;
          description
           "This enables or disables IGMP Snooping Fast-Leave on specified interface.";
          smiv2:defval disable;
          smiv2:max-access read-write;
          smiv2:oid 1.3.6.1.4.1.1332.1.1.5.3.8.4.1.6;
        }

        leaf msanSwitchIGMPSnoopingStaticIntfMulticastRouterMode {
          type enumeration {
            enum enable {
              value 1;
            }
            enum disable {
              value 2;
            }
          }
          description
           "Mode of static IGMP Mrouter on selected interface.";
          smiv2:max-access read-write;
          smiv2:oid 1.3.6.1.4.1.1332.1.1.5.3.8.4.1.7;
        }

        leaf msanSwitchIGMPSnoopingIntfVlanIDs {
          type iskratel-msan:VlanList;
          status deprecated;
          description
           "This field lists all the VlanIDs which include the selected interface.";
          smiv2:max-access read-only;
          smiv2:oid 1.3.6.1.4.1.1332.1.1.5.3.8.4.1.8;
        }
      }
    }

    container msanSwitchIGMPVlanStaticMrouterTable {
      status deprecated;
      description
       "Description.";
      smiv2:oid 1.3.6.1.4.1.1332.1.1.5.3.8.5;

      list msanSwitchIGMPVlanStaticMrouterEntry {
        key "ifIndex dot1qVlanIndex";
        status deprecated;
        description
         "Description.";
        smiv2:oid 1.3.6.1.4.1.1332.1.1.5.3.8.5.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanSwitchIGMPVlanStaticMrouterEnableState {
          type snmpv2-tc:RowStatus;
          status deprecated;
          description
           "Object used to create a new row or modify or destroy an existing row in manner described in the definition of the RowStatus textual.
            Supported states are Active(1), CreateAndGo(4) and Destroy(6).
            
            Row is created with CreateAndGo(4). This enables IGMP Mrouter on a per-interface per-vlan basis and
            the row goes to Active(1). The row is removed with Destroy(6) and IGMP Mrouter on this interface/VLAN pair is disabled.
            
            Values NotInService(2), NotReady(3) and CreateAndWait(5) are not supported.";
          smiv2:max-access read-write;
          smiv2:oid 1.3.6.1.4.1.1332.1.1.5.3.8.5.1.1;
        }
      }
    }

    container msanSwitchIGMPSnoopingVlanTable {
      description
       "A table of the IGMP Snooping Vlan configuration entries.";
      reference
       "agentSwitchIGMPSnoopingVlanTable - 1.3.6.1.4.1.6132.1.1.1.2.8.8.1";
      smiv2:oid 1.3.6.1.4.1.1332.1.1.5.3.8.6;

      list msanSwitchIGMPSnoopingVlanEntry {
        key dot1qVlanIndex;
        description
         "Represents entry for a IGMP Snooping Vlan.";
        smiv2:oid 1.3.6.1.4.1.1332.1.1.5.3.8.6.1;

        leaf dot1qVlanIndex {
          type leafref {
            path "/q-bridge:Q-BRIDGE-MIB/q-bridge:dot1qVlanCurrentTable/q-bridge:dot1qVlanCurrentEntry/q-bridge:dot1qVlanIndex";
          }
        }

        leaf msanSwitchIGMPSnoopingVlanAdminMode {
          type enumeration {
            enum disable {
              value 0;
            }
            enum enable {
              value 1;
            }
          }
          status deprecated;
          description
           "This enables or disables IGMP Snooping on a selected Vlan interface.";
          smiv2:defval disable;
          smiv2:max-access read-write;
          smiv2:oid 1.3.6.1.4.1.1332.1.1.5.3.8.6.1.1;
        }

        leaf msanSwitchIGMPSnoopingVlanGroupMembershipInterval {
          type int32 {
            range "2..3600";
          }
          status deprecated;
          description
           "The amount of time in seconds that a switch will wait for a report
            from a particular group on the selected vlan before deleting the
            interface participating in the vlan from the entry. This value must
            be greater than agentSwitchIGMPSnoopingIntfMaxResponseTime.";
          smiv2:defval 260;
          smiv2:max-access read-write;
          smiv2:oid 1.3.6.1.4.1.1332.1.1.5.3.8.6.1.2;
        }

        leaf msanSwitchIGMPSnoopingVlanMaxResponseTime {
          type int32 {
            range "1..3599";
          }
          status deprecated;
          description
           "The amount of time in seconds a switch will wait after sending
            a query on the selected vlan because it did not receive a report for
            a particular group in the interface participating in the vlan.
            This value must be less than
            agentSwitchIGMPSnoopingIntfGroupMembershipInterval.";
          smiv2:defval 10;
          smiv2:max-access read-write;
          smiv2:oid 1.3.6.1.4.1.1332.1.1.5.3.8.6.1.3;
        }

        leaf msanSwitchIGMPSnoopingVlanFastLeaveAdminMode {
          type enumeration {
            enum disable {
              value 0;
            }
            enum enable {
              value 1;
            }
          }
          status deprecated;
          description
           "This enables or disables IGMP Snooping on the selected vlan.";
          smiv2:defval disable;
          smiv2:max-access read-write;
          smiv2:oid 1.3.6.1.4.1.1332.1.1.5.3.8.6.1.4;
        }

        leaf msanSwitchIGMPSnoopingVlanMRPExpirationTime {
          type int32 {
            range "0..3600";
          }
          status deprecated;
          description
           "The amount of time in seconds that a switch will wait for a query to be
            received on the selected interface participating in the vlan before the
            interface is removed from the list of interfaces with multicast routers
            attached. This parameter is configurable only for exisiting Vlans.";
          smiv2:defval 0;
          smiv2:max-access read-write;
          smiv2:oid 1.3.6.1.4.1.1332.1.1.5.3.8.6.1.5;
        }

        leaf msanSwitchIGMPSnoopingVlanAdminState {
          type enumeration {
            enum disableAndDiscard {
              value 0;
            }
            enum disableAndBroadcast {
              value 1;
            }
            enum enable {
              value 2;
            }
            enum enableAndUnknownGroupFlood {
              value 3;
            }
          }
          description
           "IGMP Snooping state on a selected Vlan interface.
            
            This parameter is ignored if global msanIgmpSnoopingAdminState value
            is disableAndDiscard(0) or disableAndBroadcast(1).";
          smiv2:defval disableAndDiscard;
          smiv2:max-access read-write;
          smiv2:oid 1.3.6.1.4.1.1332.1.1.5.3.8.6.1.6;
        }
      }
    }

    container msanSwitchIGMPProxyVlanTable {
      description
       "A table of the IGMP Proxy Vlan configuration entries.";
      smiv2:oid 1.3.6.1.4.1.1332.1.1.5.3.8.7;

      list msanSwitchIGMPProxyVlanEntry {
        key "dot1qVlanIndex msanSwitchIGMPProxyVlanIpAddr";
        description
         " ";
        smiv2:oid 1.3.6.1.4.1.1332.1.1.5.3.8.7.1;

        leaf dot1qVlanIndex {
          type leafref {
            path "/q-bridge:Q-BRIDGE-MIB/q-bridge:dot1qVlanCurrentTable/q-bridge:dot1qVlanCurrentEntry/q-bridge:dot1qVlanIndex";
          }
        }

        leaf msanSwitchIGMPProxyVlanIpAddr {
          type inet:ipv4-address;
          description
           "IGMP Proxy IP address. If set to 0.0.0.0, default IP address is
            used (IP address of MN interface -> msanNetworkIPAddress).";
          smiv2:max-access not-accessible;
          smiv2:oid 1.3.6.1.4.1.1332.1.1.5.3.8.7.1.1;
        }

        leaf msanSwitchIGMPProxyVlanRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.8.7.1.2;
        }
      }
    }

    container msanIgmpPortStatTable {
      description
       "Description.";
      smiv2:oid 1.3.6.1.4.1.1332.1.1.5.3.8.8.2;

      list msanIgmpPortStatEntry {
        key ifIndex;
        description
         "Description.";
        smiv2:oid 1.3.6.1.4.1.1332.1.1.5.3.8.8.2.1;

        leaf ifIndex {
          type leafref {
            path "/if-mib:interfaces/if-mib:ifEntry/if-mib:ifIndex";
          }
        }

        leaf msanIgmpPortStatRxV1 {
          type yang:counter32;
          description
           "Number of received IGMP v1 packets.";
          smiv2:max-access read-only;
          smiv2:oid 1.3.6.1.4.1.1332.1.1.5.3.8.8.2.1.1;
        }

        leaf msanIgmpPortStatTxV1 {
          type yang:counter32;
          description
           "Number of transmitted IGMP v1 packets.";
          smiv2:max-access read-only;
          smiv2:oid 1.3.6.1.4.1.1332.1.1.5.3.8.8.2.1.2;
        }

        leaf msanIgmpPortStatRxV2Join {
          type yang:counter32;
          description
           "Number of received IGMP v2 join packets.";
          smiv2:max-access read-only;
          smiv2:oid 1.3.6.1.4.1.1332.1.1.5.3.8.8.2.1.3;
        }

        leaf msanIgmpPortStatTxV2Join {
          type yang:counter32;
          description
           "Number of transmitted IGMP v2 join packets.";
          smiv2:max-access read-only;
          smiv2:oid 1.3.6.1.4.1.1332.1.1.5.3.8.8.2.1.4;
        }

        leaf msanIgmpPortStatRxV2Leave {
          type yang:counter32;
          description
           "Number of received IGMP v2 leave packets.";
          smiv2:max-access read-only;
          smiv2:oid 1.3.6.1.4.1.1332.1.1.5.3.8.8.2.1.5;
        }

        leaf msanIgmpPortStatTxV2Leave {
          type yang:counter32;
          description
           "Number of transmitted IGMP v2 leave packets.";
          smiv2:max-access read-only;
          smiv2:oid 1.3.6.1.4.1.1332.1.1.5.3.8.8.2.1.6;
        }

        leaf msanIgmpPortStatRxV3Report {
          type yang:counter32;
          description
           "Number of received IGMP v3 report packets.";
          smiv2:max-access read-only;
          smiv2:oid 1.3.6.1.4.1.1332.1.1.5.3.8.8.2.1.7;
        }

        leaf msanIgmpPortStatTxV3Report {
          type yang:counter32;
          description
           "Number of transmitted IGMP v3 report packets.";
          smiv2:max-access read-only;
          smiv2:oid 1.3.6.1.4.1.1332.1.1.5.3.8.8.2.1.8;
        }

        leaf msanIgmpPortStatRxQuery {
          type yang:counter32;
          description
           "Number of received IGMP query  packets.";
          smiv2:max-access read-only;
          smiv2:oid 1.3.6.1.4.1.1332.1.1.5.3.8.8.2.1.9;
        }

        leaf msanIgmpPortStatRxError {
          type yang:counter32;
          description
           "Number of received corrupted or unknown IGMP packets.";
          smiv2:max-access read-only;
          smiv2:oid 1.3.6.1.4.1.1332.1.1.5.3.8.8.2.1.10;
        }

        leaf msanIgmpPortStatRxBlockByIgmpFilter {
          type yang:counter32;
          description
           "Number of received  IGMP packets blocked by IGMP filter.";
          smiv2:max-access read-only;
          smiv2:oid 1.3.6.1.4.1.1332.1.1.5.3.8.8.2.1.11;
        }

        leaf msanIgmpPortStatRxBlockByMcastAcl {
          type yang:counter32;
          description
           "Number of received  IGMP packets blocked by Multicast ACL.";
          smiv2:max-access read-only;
          smiv2:oid 1.3.6.1.4.1.1332.1.1.5.3.8.8.2.1.12;
        }

        leaf msanIgmpPortStatRxBlockByMcastCac {
          type yang:counter32;
          description
           "Number of received  IGMP packets blocked by Multicast CAC.";
          smiv2:max-access read-only;
          smiv2:oid 1.3.6.1.4.1.1332.1.1.5.3.8.8.2.1.13;
        }

        leaf msanIgmpPortStatTxQuery {
          type yang:counter32;
          description
           "Number of transmitted IGMP query  packets.";
          smiv2:max-access read-only;
          smiv2:oid 1.3.6.1.4.1.1332.1.1.5.3.8.8.2.1.14;
        }

        leaf msanIgmpPortStatRxBlockByIgmpVersion {
          type yang:counter32;
          description
           "Number of received  IGMP packets blocked by IGMP Version.";
          smiv2:max-access read-only;
          smiv2:oid 1.3.6.1.4.1.1332.1.1.5.3.8.8.2.1.15;
        }
      }
    }

    container msanPortTable {
      description
       "Description.";
      smiv2:oid 1.3.6.1.4.1.1332.1.1.5.3.10.2;

      list msanPortEntry {
        key ifName;
        description
         "Description.";
        smiv2:oid 1.3.6.1.4.1.1332.1.1.5.3.10.2.1;

        leaf ifName {
          type if:interface-ref;
          description 
           "A reference to the name of a configured network layer
            interface.";
        }

        leaf msanPortMNFlag {
          type enumeration {
            enum enable {
              value 1;
            }
            enum disable {
              value 2;
            }
          }
          description
           "This object determines whether to allow or not allow management access to a specific link. The factory default is enabled. ";
          smiv2:defval enable;
          smiv2:max-access read-write;
          smiv2:oid 1.3.6.1.4.1.1332.1.1.5.3.10.2.1.1;
        }

        leaf msanPortMasterSlave {
          type enumeration {
            enum none {
              value 1;
            }
            enum master {
              value 2;
            }
            enum slave {
              value 3;
            }
          }
          description
           "This object determines whether Gb port should be master or slave. Set to none when
            auto-negotiation and for non-Gb ports.";
          smiv2:defval none;
          smiv2:max-access read-write;
          smiv2:oid 1.3.6.1.4.1.1332.1.1.5.3.10.2.1.6;
        }

        leaf msanPortNegCapAdvertisedBits {
          type bits {
            bit bOther {
              position 0;
            }
            bit b10baseT {
              position 1;
            }
            bit b10baseTFD {
              position 2;
            }
            bit b100baseT4 {
              position 3;
            }
            bit b100baseTX {
              position 4;
            }
            bit b100baseTXFD {
              position 5;
            }
            bit b100baseT2 {
              position 6;
            }
            bit b100baseT2FD {
              position 7;
            }
            bit bFdxPause {
              position 8;
            }
            bit bFdxAPause {
              position 9;
            }
            bit bFdxSPause {
              position 10;
            }
            bit bFdxBPause {
              position 11;
            }
            bit b1000baseX {
              position 12;
            }
            bit b1000baseXFD {
              position 13;
            }
            bit b1000baseT {
              position 14;
            }
            bit b1000baseTFD {
              position 15;
            }
          }
          description
           "A value that uniquely identifies the set of capabilities advertised by
            the local auto-negotiation entity.
            
            Note that the local auto-negotiation entity may advertise some capabilities
            beyond the scope of this MIB. This is indicated by returning the bit value
            bOther in addition to any bit values for capabilities that are listed above.
            
            Only b1000baseXFD(13) and b1000baseTFD(15) are currently supported.";
          reference
           "[IEEE 802.3 Std], 30.6.1.1.6, aAutoNegAdvertisedTechnologyAbility;
            ifMauAutoNegCapAdvertisedBits (OID 1.3.6.1.2.1.26.5.1.1.11)";
          smiv2:max-access read-write;
          smiv2:oid 1.3.6.1.4.1.1332.1.1.5.3.10.2.1.7;
        }

        leaf msanPortSpeedDuplex {
          type enumeration {
            enum speed10MbpsHD {
              value 10;
            }
            enum speed10MbpsFD {
              value 11;
            }
            enum speed100MbpsHD {
              value 15;
            }
            enum speed100MbpsFD {
              value 16;
            }
            enum speed100MbpsFDFiber {
              value 18;
            }
            enum speed1000MbpsFDFiber {
              value 26;
            }
            enum speed1000MbpsFD {
              value 30;
            }
            enum speed10GbpsFDFiber {
              value 31;
            }
          }
          description
           "Speed and duplex mode of the interface.";
          smiv2:max-access read-write;
          smiv2:oid 1.3.6.1.4.1.1332.1.1.5.3.10.2.1.8;
        }

        leaf msanPortStpP2PAutoState {
          type enumeration {
            enum enable {
              value 1;
            }
            enum disable {
              value 2;
            }
          }
          description
           "The field extends ISKRATEL-MSAN-BASICCONF-MIB.agentStpCstPortOperPointToPoint by the <auto> value.";
          smiv2:defval enable;
          smiv2:max-access read-write;
          smiv2:oid 1.3.6.1.4.1.1332.1.1.5.3.10.2.1.20;
        }

        leaf msanPortUsageType {
          type enumeration {
            enum uplink {
              value 1;
            }
            enum access {
              value 2;
            }
          }
          description
           "This object specifies the type of an interface whether it is an uplink or access port.
            If you change this value you must save configuration and restart network element.";
          smiv2:max-access read-write;
          smiv2:oid 1.3.6.1.4.1.1332.1.1.5.3.10.2.1.21;
        }
      }
    }

    container msanPppoeIAPortTable {
      description
       "Description.";
      smiv2:oid 1.3.6.1.4.1.1332.1.1.5.3.11.2;

      list msanPppoeIAPortEntry {
        key ifIndex;
        description
         "Description.";
        smiv2:oid 1.3.6.1.4.1.1332.1.1.5.3.11.2.1;

        leaf ifIndex {
          type leafref {
            path "/if-mib:interfaces/if-mib:ifEntry/if-mib:ifIndex";
          }
        }

        leaf msanPppoeIAPortStatus {
          type enumeration {
            enum enable {
              value 1;
            }
            enum disable {
              value 2;
            }
            enum enableClient {
              value 3;
            }
            enum enableServer {
              value 4;
            }
          }
          description
           "State of PPPoE Intermadiate Agent on the port";
          smiv2:max-access read-write;
          smiv2:oid 1.3.6.1.4.1.1332.1.1.5.3.11.2.1.1;
        }

        leaf msanPppoeIAPortRemoteId {
          type binary;
          description
           "Remote Id for the port.";
          smiv2:max-access read-write;
          smiv2:oid 1.3.6.1.4.1.1332.1.1.5.3.11.2.1.2;
        }

        leaf msanPppoeIAPortCircuitType {
          type enumeration {
            enum trusted {
              value 1;
            }
            enum untrusted {
              value 2;
            }
          }
          description
           "PPPoE IA Circuit type per port.";
          smiv2:defval untrusted;
          smiv2:max-access read-write;
          smiv2:oid 1.3.6.1.4.1.1332.1.1.5.3.11.2.1.3;
        }

        leaf msanPppoeIAPortCircuitIdType {
          type enumeration {
            enum iskratel {
              value 1;
            }
            enum atm {
              value 3;
            }
          }
          description
           "Circuit Id syntax mode per port.";
          smiv2:max-access read-write;
          smiv2:oid 1.3.6.1.4.1.1332.1.1.5.3.11.2.1.4;
        }
      }
    }

    container msanPppoeIaPortStatisticsTable {
      description
       "Description.";
      smiv2:oid 1.3.6.1.4.1.1332.1.1.5.3.11.3.9;

      list msanPppoeIaPortStatisticsEntry {
        key ifIndex;
        description
         "Description.";
        smiv2:oid 1.3.6.1.4.1.1332.1.1.5.3.11.3.9.1;

        leaf ifIndex {
          type leafref {
            path "/if-mib:interfaces/if-mib:ifEntry/if-mib:ifIndex";
          }
        }

        leaf msanPppoeIaPortStatPADI {
          type yang:counter32;
          description
           "Number of PADI packets on the port. ";
          smiv2:max-access read-only;
          smiv2:oid 1.3.6.1.4.1.1332.1.1.5.3.11.3.9.1.1;
        }

        leaf msanPppoeIaPortStatPADR {
          type yang:counter32;
          description
           "Number of PADR packets on the port. ";
          smiv2:max-access read-only;
          smiv2:oid 1.3.6.1.4.1.1332.1.1.5.3.11.3.9.1.2;
        }

        leaf msanPppoeIaPortStatPADO {
          type yang:counter32;
          description
           "Number of PADO packets on the port. ";
          smiv2:max-access read-only;
          smiv2:oid 1.3.6.1.4.1.1332.1.1.5.3.11.3.9.1.3;
        }

        leaf msanPppoeIaPortStatPADS {
          type yang:counter32;
          description
           "Number of PADS packets on the port. ";
          smiv2:max-access read-only;
          smiv2:oid 1.3.6.1.4.1.1332.1.1.5.3.11.3.9.1.4;
        }

        leaf msanPppoeIaPortStatPADT {
          type yang:counter32;
          description
           "Number of PADT packets on the port. ";
          smiv2:max-access read-only;
          smiv2:oid 1.3.6.1.4.1.1332.1.1.5.3.11.3.9.1.5;
        }

        leaf msanPppoeIaPortStatUnsutableFrames {
          type yang:counter32;
          description
           "Number of packets with unsutable frame on the port. ";
          smiv2:max-access read-only;
          smiv2:oid 1.3.6.1.4.1.1332.1.1.5.3.11.3.9.1.6;
        }

        leaf msanPppoeIaPortStatUnknownFrames {
          type yang:counter32;
          description
           "Number of packets with unknown frame on the port. ";
          smiv2:max-access read-only;
          smiv2:oid 1.3.6.1.4.1.1332.1.1.5.3.11.3.9.1.7;
        }

        leaf msanPppoeIaPortStatInvalidFrames {
          type yang:counter32;
          description
           "Number of packets with invalid frame on the port. ";
          smiv2:max-access read-only;
          smiv2:oid 1.3.6.1.4.1.1332.1.1.5.3.11.3.9.1.8;
        }
      }
    }

    container msanPppoeIaVlanTable {
      description
       "Description.";
      smiv2:oid 1.3.6.1.4.1.1332.1.1.5.3.11.4;

      list msanPppoeIaVlanEntry {
        key dot1qVlanIndex;
        description
         "Description.";
        smiv2:oid 1.3.6.1.4.1.1332.1.1.5.3.11.4.1;

        leaf dot1qVlanIndex {
          type leafref {
            path "/q-bridge:Q-BRIDGE-MIB/q-bridge:dot1qVlanCurrentTable/q-bridge:dot1qVlanCurrentEntry/q-bridge:dot1qVlanIndex";
          }
        }

        leaf msanPppoeIaVlanStatus {
          type enumeration {
            enum enable {
              value 1;
            }
            enum disable {
              value 2;
            }
          }
          description
           "State of PPPoE Intermadiate Agent per VLAN.";
          smiv2:max-access read-write;
          smiv2:oid 1.3.6.1.4.1.1332.1.1.5.3.11.4.1.1;
        }
      }
    }

    container msanIpAclRuleTable {
      description
       "This table extends aclTable/aclRuleTable.";
      smiv2:oid 1.3.6.1.4.1.1332.1.1.5.3.12.2;

      list msanIpAclRuleEntry {
        key "msanIpAclIndex msanIpAclRuleIndex";
        description
         "This table extends aclTable/aclRuleTable.";
        smiv2:oid 1.3.6.1.4.1.1332.1.1.5.3.12.2.1;

        leaf msanIpAclIndex {
                    type leafref {
                        path "/iskratel-msan:ISKRATEL-MSAN-BASICCONF-MIB/iskratel-msan:aclTable/iskratel-msan:aclEntry/iskratel-msan:aclIndex";
                    }

          description
           "This is aclIndex in aclTable";
          smiv2:max-access not-accessible;
          smiv2:oid 1.3.6.1.4.1.1332.1.1.5.3.12.2.1.1;
        }

        leaf msanIpAclRuleIndex {
                    type leafref {
                        path "/iskratel-msan:ISKRATEL-MSAN-BASICCONF-MIB/iskratel-msan:aclRuleTable/iskratel-msan:aclRuleEntry/iskratel-msan:aclRuleIndex";
                    }

          description
           "The index of the IP ACL rule (aclRuleIndex in aclRuleTable).";
          smiv2:max-access not-accessible;
          smiv2:oid 1.3.6.1.4.1.1332.1.1.5.3.12.2.1.2;
        }

        leaf msanIpAclRuleDestMacAddr {
          type yang:mac-address;
          description
           "The Destination MAC address used in the Advanced IP ACL Classification.
            
            Advanced IP ACL:    msanIpAclIndex  value in range 200 ... 299";
          smiv2:max-access read-write;
          smiv2:oid 1.3.6.1.4.1.1332.1.1.5.3.12.2.1.9;
        }

        leaf msanIpAclRuleDestMacMask {
          type yang:mac-address;
          description
           "The Destination MAC address mask used in the Advanced IP Classification.
            
            This mask value identifies the portion of the msanIpAclRuleDestMacAddr
            that is compared against a packet. A non-contiguous mask value is
            permitted.
            
            Advanced IP ACL:    msanIpAclIndex value in range 200 ... 299";
          smiv2:max-access read-write;
          smiv2:oid 1.3.6.1.4.1.1332.1.1.5.3.12.2.1.10;
        }

        leaf msanIpAclRuleSrcMacAddr {
          type yang:mac-address;
          description
           "The Source MAC address used in the Advanced IP ACL Classification.
            
            Advanced IP ACL:    msanIpAclIndex value in range 200 ... 299";
          smiv2:max-access read-write;
          smiv2:oid 1.3.6.1.4.1.1332.1.1.5.3.12.2.1.11;
        }

        leaf msanIpAclRuleSrcMacMask {
          type yang:mac-address;
          description
           "The Source MAC address mask used in the Advanced IP Classification.
            
            This mask value identifies the portion of the msanIpAclRuleSrcMacAddr
            that is compared against a packet. A non-contiguous mask value is
            permitted.
            
            Advanced IP ACL:    msanIpAclIndex value in range 200 ... 299";
          smiv2:max-access read-write;
          smiv2:oid 1.3.6.1.4.1.1332.1.1.5.3.12.2.1.12;
        }

        leaf msanIpAclRuleCos {
          type int32 {
            range "0..7";
          }
          description
           "The Class of Service (COS) used in the Advanced IP Classification.
            
            This is the three-bit user priority field in the 802.1Q tag
            header of a tagged Ethernet frame. For frames containing a
            double VLAN tag, this field is located in the first/outer tag.
            
            Advanced IP ACL:    msanIpAclIndex value in range 200 ... 299";
          smiv2:max-access read-write;
          smiv2:oid 1.3.6.1.4.1.1332.1.1.5.3.12.2.1.13;
        }

        leaf msanIpAclRuleCos2 {
          type int32 {
            range "0..7";
          }
          description
           "The Secondary Class of Service (COS) used in the Advanced IP Classification.
            
            This is the three-bit user priority field in the second 802.1Q tag
            header of a tagged Ethernet frame.
            
            Advanced IP ACL:    msanIpAclIndex value in range 200 ... 299";
          smiv2:max-access read-write;
          smiv2:oid 1.3.6.1.4.1.1332.1.1.5.3.12.2.1.14;
        }

        leaf msanIpAclRuleCVlanId {
          type int32 {
            range "0..4095";
          }
          description
           "The C-customer VLAN ID value used in the Advanced IP Classification.
            
            The VLAN ID field is defined as the 12-bit VLAN identifier
            in the second 802.1Q tag header of a tagged Ethernet frame.
            
            Advanced IP ACL:    msanIpAclIndex value in range 200 ... 299";
          smiv2:max-access read-write;
          smiv2:oid 1.3.6.1.4.1.1332.1.1.5.3.12.2.1.17;
        }

        leaf msanIpAclRuleSVlanId {
          type int32 {
            range "0..4095";
          }
          description
           "The S-service VLAN ID value used in the Advanced IP Classification.
            
            The VLAN ID field is defined as the 12-bit VLAN identifier
            in the 802.1Q tag header of a tagged Ethernet frame.  This is
            contained in the first/outer tag of a double VLAN tagged frame.
            
            Advanced IP ACL:    msanIpAclIndex value in range 200 ... 299";
          smiv2:max-access read-write;
          smiv2:oid 1.3.6.1.4.1.1332.1.1.5.3.12.2.1.18;
        }

        leaf msanIpAclRuleAssignCVlanId {
          type int32 {
            range "0..4095";
          }
          description
           "Assign C VLAN ID -> add (if not exists) or change.
            
            Used in the Advanced IP Classification.
            Advanced IP ACL:    msanIpAclIndex value in range 200 ... 299";
          smiv2:max-access read-write;
          smiv2:oid 1.3.6.1.4.1.1332.1.1.5.3.12.2.1.19;
        }

        leaf msanIpAclRuleAssignCPcp {
          type int32 {
            range "0..4095";
          }
          description
           "Assign Customer PCP (Priority Code Point) -
            PCP is also known as Class of Service (CoS) bits.
            A value of -1 indicates that parameter has not been defined.
            This parameter can be used only if msanIpAclRuleAssignCVlanId is already set.
            
            Used in the Advanced IP Classification.
            Advanced IP ACL:    msanIpAclIndex value in range 200 ... 299";
          smiv2:max-access read-write;
        }

        leaf msanIpAclRuleAssignSVlanId {
          type int32 {
            range "0..4095";
          }
          description
           "Assign S VLAN ID -> add (if not exists) or change.
            
            Used in the Advanced IP Classification.
            Advanced IP ACL:    msanIpAclIndex value in range 200 ... 299";
          smiv2:max-access read-write;
          smiv2:oid 1.3.6.1.4.1.1332.1.1.5.3.12.2.1.20;
        }

        leaf msanIpAclRuleAssignSPcp {
          type int32 {
            range "0..4095";
          }
          description
           "Assign Service PCP  (Priority Code Point).
            PCP is also known as Class of Service (CoS) bits.
            A value of -1 indicates that parameter has not been defined.
            This parameter can be used only if msanIpAclRuleAssignSVlanId is already set.
            
            Used in the Advanced IP Classification.
            Advanced IP ACL:    msanIpAclIndex value in range 200 ... 299";
          smiv2:max-access read-write;
        }

        leaf msanIpAclRuleRemoveSVlanId {
          type enumeration {
            enum enable {
              value 1;
            }
            enum disable {
              value 2;
            }
          }
          description
           "Remove S-service VLAN ID.
            
            Used in the Advanced IP Classification.
            Advanced IP ACL:    msanIpAclIndex value in range 200 ... 299";
          smiv2:max-access read-write;
          smiv2:oid 1.3.6.1.4.1.1332.1.1.5.3.12.2.1.21;
        }

        leaf msanIpAclRuleSVlanIdRangeStart {
          type uint32 {
            range "0..4095";
          }
          description
           "The S-service VLAN ID range start value used in the Advanced IP Classification.
            Setting this value greater than the current msanIpAclRuleSVlanIdRangeEnd
            changes the VLAN ID range end to the same value as the range start.
            
            Advanced IP ACL:    msanIpAclIndex value in range 200 ... 299";
          smiv2:max-access read-write;
          smiv2:oid 1.3.6.1.4.1.1332.1.1.5.3.12.2.1.26;
        }

        leaf msanIpAclRuleSVlanIdRangeEnd {
          type uint32 {
            range "0..4095";
          }
          description
           "The S-service VLAN ID range end value used in the Advanced IP Classification.
            Setting this value less than the current msanIpAclRuleSVlanIdRangeStart
            changes the VLAN ID range start to the same value as the range end.
            
            Advanced IP ACL:    msanIpAclIndex value in range 200 ... 299";
          smiv2:max-access read-write;
          smiv2:oid 1.3.6.1.4.1.1332.1.1.5.3.12.2.1.27;
        }

        leaf msanIpAclRuleCVlanIdRangeStart {
          type uint32 {
            range "0..4095";
          }
          description
           "The C-customer VLAN ID range start value used in the Advanced IP Classification.
            Setting this value greater than the current msanIpAclRuleCVlanIdRangeEnd
            changes the VLAN ID range end to the same value as the range start.
            
            Advanced IP ACL:    msanIpAclIndex value in range 200 ... 299";
          smiv2:max-access read-write;
          smiv2:oid 1.3.6.1.4.1.1332.1.1.5.3.12.2.1.28;
        }

        leaf msanIpAclRuleCVlanIdRangeEnd {
          type uint32 {
            range "0..4095";
          }
          description
           "The C-customer VLAN ID range end value used in the Advanced IP Classification.
            Setting this value less than the current msanIpAclRuleCVlanIdRangeStart
            changes the VLAN ID range start to the same value as the range end.
            
            Advanced IP ACL:    msanIpAclIndex value in range 200 ... 299";
          smiv2:max-access read-write;
          smiv2:oid 1.3.6.1.4.1.1332.1.1.5.3.12.2.1.29;
        }

        leaf msanIpAclRuleSrcIpv6Address {
          type inet-address:InetAddressIPv6;
          description
           "The Source IPv6 Address used in the ACL Classification.";
          smiv2:max-access read-write;
          smiv2:oid 1.3.6.1.4.1.1332.1.1.5.3.12.2.1.31;
        }

        leaf msanIpAclRuleSrcIpv6AddressMaskLen {
          type int32 {
            range "0..128";
          }
          description
           "The length of the prefix (in bits) associated with the
            IPv6 source address of this entry (msanIpAclRuleSrcIpv6Address).
            
            Value 0 indicates that parameter has not been defined.";
          smiv2:defval 0;
          smiv2:max-access read-write;
          smiv2:oid 1.3.6.1.4.1.1332.1.1.5.3.12.2.1.32;
        }

        leaf msanIpAclRuleDestIpv6Address {
          type inet-address:InetAddressIPv6;
          description
           "The Destination IPv6 Address used in the ACL Classification.";
          smiv2:max-access read-write;
          smiv2:oid 1.3.6.1.4.1.1332.1.1.5.3.12.2.1.33;
        }

        leaf msanIpAclRuleDestIpv6AddressMaskLen {
          type int32 {
            range "0..128";
          }
          description
           "The length of the prefix (in bits) associated with the
            IPv6 destination address of this entry (msanIpAclRuleDestIpv6Address).
            
            Value 0 indicates that parameter has not been defined.";
          smiv2:defval 0;
          smiv2:max-access read-write;
          smiv2:oid 1.3.6.1.4.1.1332.1.1.5.3.12.2.1.34;
        }
      }
    }

    container msanMacAclRuleTable {
      description
       "This table extends aclMacTable/aclMacRuleTable.";
      smiv2:oid 1.3.6.1.4.1.1332.1.1.5.3.12.3;

      list msanMacAclRuleEntry {
        key "msanMacAclName msanMacAclRuleIndex";
        description
         "This table extends aclMacTable/aclMacRuleTable.";
        smiv2:oid 1.3.6.1.4.1.1332.1.1.5.3.12.3.1;

        leaf msanMacAclName {
                    type leafref {
                        path "/iskratel-msan:ISKRATEL-MSAN-BASICCONF-MIB/iskratel-msan:aclMacTable/iskratel-msan:aclMacEntry/iskratel-msan:aclMacName";
                    }

          description
           "This is aclMacIndex in aclMacTable";
          smiv2:max-access not-accessible;
        }

        leaf msanMacAclRuleIndex {
                    type leafref {
                        path "/iskratel-msan:ISKRATEL-MSAN-BASICCONF-MIB/iskratel-msan:aclMacRuleTable/iskratel-msan:aclMacRuleEntry/iskratel-msan:aclMacRuleIndex";
                    }

          description
           "The index of the MAC ACL rule (aclMACRuleIndex in aclMACRuleTable).";
          smiv2:max-access not-accessible;
          smiv2:oid 1.3.6.1.4.1.1332.1.1.5.3.12.3.1.2;
        }

        leaf msanMacAclRuleCVlanId {
          type int32;
          description
           "C-customer Vlan ID";
          smiv2:max-access read-write;
          smiv2:oid 1.3.6.1.4.1.1332.1.1.5.3.12.3.1.8;
        }

        leaf msanMacAclRuleSVlanId {
          type int32;
          description
           "S-service Vlan ID";
          smiv2:max-access read-write;
          smiv2:oid 1.3.6.1.4.1.1332.1.1.5.3.12.3.1.9;
        }

        leaf msanMacAclRuleAssignCVlanId {
          type int32 {
            range "0..4095";
          }
          description
           "Assign C-customer  VLAN ID -> add (if not exists) or change.";
          smiv2:max-access read-write;
          smiv2:oid 1.3.6.1.4.1.1332.1.1.5.3.12.3.1.10;
        }

        leaf msanMacAclRuleAssignCPcp {
          type int32 {
            range "0..4095";
          }
          description
           "Assign Customer PCP (Priority Code Point) -
            PCP is also known as Class of Service (CoS) bits.
            A value of -1 indicates that parameter has not been defined.
            This parameter can be used only if msanMacAclRuleAssignCVlanId is already set.";
          smiv2:max-access read-write;
        }

        leaf msanMacAclRuleAssignSVlanId {
          type int32 {
            range "0..4095";
          }
          description
           "Assign S-service VLAN ID -> add (if not exists) or change.";
          smiv2:max-access read-write;
          smiv2:oid 1.3.6.1.4.1.1332.1.1.5.3.12.3.1.11;
        }

        leaf msanMacAclRuleAssignSPcp {
          type int32 {
            range "0..4095";
          }
          description
           "Assign Service PCP (Priority Code Point) -
            PCP is also known as Class of Service (CoS) bits.
            A value of -1 indicates that parameter has not been defined.
            This parameter can be used only if msanMacAclRuleAssignSVlanId is already set.";
          smiv2:max-access read-write;
        }

        leaf msanMacAclRuleRemoveSVlanId {
          type enumeration {
            enum enable {
              value 1;
            }
            enum disable {
              value 2;
            }
          }
          description
           "Remove S-service VLAN ID.";
          smiv2:max-access read-write;
          smiv2:oid 1.3.6.1.4.1.1332.1.1.5.3.12.3.1.12;
        }

        leaf msanMacAclRuleSVlanIdRangeStart {
          type uint32 {
            range "0..4095";
          }
          description
           "The S-service VLAN ID range start value.
            Setting this value greater than the current msanMacAclRuleSVlanIdRangeEnd
            changes the VLAN ID range end to the same value as the range start.";
          smiv2:max-access read-write;
          smiv2:oid 1.3.6.1.4.1.1332.1.1.5.3.12.3.1.13;
        }

        leaf msanMacAclRuleSVlanIdRangeEnd {
          type uint32 {
            range "0..4095";
          }
          description
           "The S-service VLAN ID range end value.
            Setting this value less than the current msanMacAclRuleSVlanIdRangeStart
            changes the VLAN ID range start to the same value as the range end.";
          smiv2:max-access read-write;
          smiv2:oid 1.3.6.1.4.1.1332.1.1.5.3.12.3.1.14;
        }

        leaf msanMacAclRuleCVlanIdRangeStart {
          type uint32 {
            range "0..4095";
          }
          description
           "The C-customer VLAN ID range start value.
            Setting this value greater than the current msanMacAclRuleCVlanIdRangeEnd
            changes the VLAN ID range end to the same value as the range start.";
          smiv2:max-access read-write;
          smiv2:oid 1.3.6.1.4.1.1332.1.1.5.3.12.3.1.15;
        }

        leaf msanMacAclRuleCVlanIdRangeEnd {
          type uint32 {
            range "0..4095";
          }
          description
           "The C-customer VLAN ID range end value.
            Setting this value less than the current msanMacAclRuleCVlanIdRangeStart
            changes the VLAN ID range start to the same value as the range end.";
          smiv2:max-access read-write;
          smiv2:oid 1.3.6.1.4.1.1332.1.1.5.3.12.3.1.16;
        }
      }
    }

    container msanCosQueueControlTable {
      description
       "Description.";
      smiv2:oid 1.3.6.1.4.1.1332.1.1.5.3.12.4;

      list msanCosQueueControlEntry {
        key ifIndex;
        description
         "Description.";
        smiv2:oid 1.3.6.1.4.1.1332.1.1.5.3.12.4.1;

        leaf ifIndex {
          type leafref {
            path "/if-mib:interfaces/if-mib:ifEntry/if-mib:ifIndex";
          }
        }

        leaf msanCosQueueControlIntfBurstSize {
          type int32;
          units kilobyte;
          description
           "Specifies the maximum number of uncommitted bytes that the switch will try to send into the network. It is the number of bytes that are sent at a rate,
            higher than committed and that the next device in the network must be able to buffer without notifying a congestion. Default value is 0.
            Valid values are 16, 20, 28, 40, 76, 140, 268 and 524 kilobytes. Configuring shaping rate without burst size will take the maximum possible value of burst, which is 524 KB. ";
          smiv2:max-access read-write;
          smiv2:oid 1.3.6.1.4.1.1332.1.1.5.3.12.4.1.1;
        }

        leaf msanCosQueueIntfShapingRate {
          type uint32 {
            range "0..10000000";
          }
          units kbps;
          description
           "Specifies the maximum bandwidth allowed, typically used to shape
            the outbound transmission rate. This value is controlled independently
            of any per-queue maximum bandwidth configuration. It is effectively a
            second-level shaping mechanism.
            Default value is 0. Valid Range is 0 to 10000000 kbps. The value 0 means
            maximum is unlimited.";
          smiv2:max-access read-write;
          smiv2:oid 1.3.6.1.4.1.1332.1.1.5.3.12.4.1.2;
        }
      }
    }

    container msanCosQueueTable {
      description
       "Table of class-of-service queue configuration
        parameters for the specified interface.
        
        This is extension of the table agentCosQueueTable. ";
      reference
       "agentCosQueueTable  - 1.3.6.1.4.1.6132.1.1.3.3.2.4";
      smiv2:oid 1.3.6.1.4.1.1332.1.1.5.3.12.5;

      list msanCosQueueEntry {
        key "ifIndex msanCosQueueIndex";
        description
         "Each entry describes a single class-of-service (COS)
          queue for a given Interface Index. The number of
          configurable COS queues for an interface vary based
          on device capabilities.
          
          All objects defined for this table entry contain a
          default value corresponding to a typical,
          non-preferential treatment of packets traversing the
          interface's COS queues.";
        reference
         "agentCosQueueTable  - 1.3.6.1.4.1.6132.1.1.3.3.2.4";
        smiv2:oid 1.3.6.1.4.1.1332.1.1.5.3.12.5.1;

        leaf ifIndex {
          type leafref {
            path "/if-mib:interfaces/if-mib:ifEntry/if-mib:ifIndex";
          }
        }

        leaf msanCosQueueIndex {
          type int32 {
            range "0..1000";
          }
          description
           "The COS queue index, numbered 0 to (n-1), where n is
            the total number of configurable interface queues for
            the device as indicated by agentCosQueueNumQueuesPerPort.
            In general, a higher numbered queue index is used to
            support higher priority traffic, although actual
            operation may be altered via configuration through
            this table.";
          smiv2:max-access not-accessible;
          smiv2:oid 1.3.6.1.4.1.1332.1.1.5.3.12.5.1.1;
        }

        leaf msanCosQueueWeight {
          type int32 {
            range "0..32";
          }
          description
           "Weight of the queue being used in egress scheduling algorithm.";
          smiv2:max-access read-write;
          smiv2:oid 1.3.6.1.4.1.1332.1.1.5.3.12.5.1.2;
        }

        leaf msanCosQueueLength {
          type int32 {
            range "2..156";
          }
          description
           "Length of the queue in kB. ";
          smiv2:defval 40;
          smiv2:max-access read-write;
          smiv2:oid 1.3.6.1.4.1.1332.1.1.5.3.12.5.1.3;
        }
      }
    }

    container msanCosMapIntfTrustTable {
      description
       "Description.";
      smiv2:oid 1.3.6.1.4.1.1332.1.1.5.3.12.6;

      list msanCosMapIntfTrustEntry {
        key ifIndex;
        description
         "Description.";
        smiv2:oid 1.3.6.1.4.1.1332.1.1.5.3.12.6.1;

        leaf ifIndex {
          type leafref {
            path "/if-mib:interfaces/if-mib:ifEntry/if-mib:ifIndex";
          }
        }

        leaf msanCosMapIntfTrustMode {
          type enumeration {
            enum untrusted {
              value 1;
            }
            enum trustDot1p {
              value 2;
            }
            enum trustIpPrecedence {
              value 3;
            }
            enum trustIpDscp {
              value 4;
            }
          }
          description
           "This is copy of LVL7 parameter agentCosMapIntfTrustMode,
            except that index 0 is not supported.
            
            The class of service trust mode of an interface.
            When set to a trusted mode, the appropriate COS
            mapping table is used as follows:
            
               trustDot1p(2) : dot1dTrafficClassTable
               trustIpPrecedence(3): agentCosMapIpPrecTable
               trustIpDscp(4): agentCosMapIpDscpTable
            
            For an untrusted(1) interface, packets are handled in
            accordance with the dot1dPortDefaultUserPriority value
            of the ingress port.";
          smiv2:max-access read-write;
          smiv2:oid 1.3.6.1.4.1.1332.1.1.5.3.12.6.1.1;
        }
      }
    }

    container msanQosProfileTable {
      description
       "Description.";
      smiv2:oid 1.3.6.1.4.1.1332.1.1.5.3.12.7;

      list msanQosProfileEntry {
        key msanQosProfileName;
        description
         "Description.";
        smiv2:oid 1.3.6.1.4.1.1332.1.1.5.3.12.7.1;

        leaf msanQosProfileName {
          type binary {
            length "1..32";
          }
          description
           "QoS profile name.";
          smiv2:max-access not-accessible;
          smiv2:oid 1.3.6.1.4.1.1332.1.1.5.3.12.7.1.1;
        }

        leaf msanQosProfileMatchInAny {
          type enumeration {
            enum enable {
              value 1;
            }
            enum disable {
              value 2;
            }
          }
          description
           "Match every incoming packet frame.";
          smiv2:defval disable;
          smiv2:max-access read-write;
          smiv2:oid 1.3.6.1.4.1.1332.1.1.5.3.12.7.1.2;
        }

        leaf msanQosProfileMatchInMacDestAddr {
          type yang:mac-address;
          description
           "Match incoming packet frame with specified destination MAC address.
            Empty string indicates that parameter has not been defined";
          smiv2:defval "";
          smiv2:max-access read-write;
          smiv2:oid 1.3.6.1.4.1.1332.1.1.5.3.12.7.1.3;
        }

        leaf msanQosProfileMatchInMacDestMask {
          type yang:mac-address;
          description
           "This mask value identifies the portion of msanQosProfileMatchInMacDestAddr that
            is compared with input packet.
            Empty string indicates that parameter has not been defined";
          smiv2:defval "";
          smiv2:max-access read-write;
          smiv2:oid 1.3.6.1.4.1.1332.1.1.5.3.12.7.1.4;
        }

        leaf msanQosProfileMatchInMacSrcAddr {
          type yang:mac-address;
          description
           "Match incoming packet frame with specified source MAC address.
            Empty string indicates that parameter has not been defined";
          smiv2:defval "";
          smiv2:max-access read-write;
          smiv2:oid 1.3.6.1.4.1.1332.1.1.5.3.12.7.1.5;
        }

        leaf msanQosProfileMatchInMacSrcMask {
          type yang:mac-address;
          description
           "This mask value identifies the portion of msanQosProfileMatchInMacSrcAddr that
            is compared with input packet.
            Empty string indicates that parameter has not been defined";
          smiv2:defval "";
          smiv2:max-access read-write;
          smiv2:oid 1.3.6.1.4.1.1332.1.1.5.3.12.7.1.6;
        }

        leaf msanQosProfileMatchInCos {
          type int32 {
            range "-1..7";
          }
          description
           "Match incoming packet frame with specified CoS value (0-7).
            A value of -1 indicates that parameter has not been defined";
          smiv2:defval -1;
          smiv2:max-access read-write;
          smiv2:oid 1.3.6.1.4.1.1332.1.1.5.3.12.7.1.7;
        }

        leaf msanQosProfileMatchInCos2 {
          type int32 {
            range "-1..7";
          }
          description
           "Match incoming packet frame with specified secondary (C-TAG) CoS value (0-7).
            A value of -1 indicates that parameter has not been defined";
          smiv2:defval -1;
          smiv2:max-access read-write;
          smiv2:oid 1.3.6.1.4.1.1332.1.1.5.3.12.7.1.8;
        }

        leaf msanQosProfileMatchInVlanId {
          type int32 {
            range "-1..4094";
          }
          description
           "Match incoming packet frame with specified VLAN ID value (1-4094).
            A value of -1 indicates that parameter has not been defined";
          smiv2:defval -1;
          smiv2:max-access read-write;
          smiv2:oid 1.3.6.1.4.1.1332.1.1.5.3.12.7.1.9;
        }

        leaf msanQosProfileMatchInVlanId2 {
          type int32 {
            range "-1..4094";
          }
          description
           "Match incoming packet frame with specified secondary (C-TAG) VLAN ID value (1-4094).
            A value of -1 indicates that parameter has not been defined";
          smiv2:defval -1;
          smiv2:max-access read-write;
          smiv2:oid 1.3.6.1.4.1.1332.1.1.5.3.12.7.1.10;
        }

        leaf msanQosProfileMatchInEthertype {
          type int32 {
            range "-1..65535";
          }
          description
           "Match incoming packet frame with specified EtherType value.
            A value of -1 indicates that parameter has not been defined.";
          smiv2:defval -1;
          smiv2:max-access read-write;
          smiv2:oid 1.3.6.1.4.1.1332.1.1.5.3.12.7.1.11;
        }

        leaf msanQosProfileMatchInIpProtocol {
          type int32 {
            range "-1..255";
          }
          description
           "Match incoming packet frame with specified IP protocol value.
            A value of -1 indicates that parameter has not been defined.
            Some of standard protocol values:
               icmp - 1
               igmp - 2
               ip - 4 (ip in ip encapsulation)
               tcp - 6
               udp - 17";
          smiv2:defval -1;
          smiv2:max-access read-write;
          smiv2:oid 1.3.6.1.4.1.1332.1.1.5.3.12.7.1.12;
        }

        leaf msanQosProfileMatchInIpSrcAddr {
          type inet:ipv4-address;
          description
           "Match incoming packet frame with specified source IP address.
            Empty string indicates that parameter has not been defined.";
          smiv2:defval "";
          smiv2:max-access read-write;
          smiv2:oid 1.3.6.1.4.1.1332.1.1.5.3.12.7.1.13;
        }

        leaf msanQosProfileMatchInIpSrcMask {
          type inet:ipv4-address;
          description
           "This mask value identifies the portion of msanQosProfileMatchInIpSrcAddr that
            is compared with input packet.
            Empty string indicates that parameter has not been defined";
          smiv2:defval "";
          smiv2:max-access read-write;
          smiv2:oid 1.3.6.1.4.1.1332.1.1.5.3.12.7.1.14;
        }

        leaf msanQosProfileMatchInIpDestAddr {
          type inet:ipv4-address;
          description
           "Match incoming packet frame with specified destination IP address.
            Empty string indicates that parameter has not been defined.";
          smiv2:defval "";
          smiv2:max-access read-write;
          smiv2:oid 1.3.6.1.4.1.1332.1.1.5.3.12.7.1.15;
        }

        leaf msanQosProfileMatchInIpDestMask {
          type inet:ipv4-address;
          description
           "This mask value identifies the portion of msanQosProfileMatchInIpDestAddr that
            is compared with input packet.
            Empty string indicates that parameter has not been defined";
          smiv2:defval "";
          smiv2:max-access read-write;
          smiv2:oid 1.3.6.1.4.1.1332.1.1.5.3.12.7.1.16;
        }

        leaf msanQosProfileMatchInIpDscp {
          type int32 {
            range "-1..63";
          }
          description
           "Match incoming packet frame with specified IP DSCP value.
            A value of -1 indicates that parameter has not been defined.";
          smiv2:defval -1;
          smiv2:max-access read-write;
          smiv2:oid 1.3.6.1.4.1.1332.1.1.5.3.12.7.1.17;
        }

        leaf msanQosProfileMatchInIpPrecedence {
          type int32 {
            range "-1..7";
          }
          description
           "Match incoming packet frame with specified IP precedence (part of TOS field) value.
            A value of -1 indicates that parameter has not been defined.";
          smiv2:defval -1;
          smiv2:max-access read-write;
          smiv2:oid 1.3.6.1.4.1.1332.1.1.5.3.12.7.1.18;
        }

        leaf msanQosProfileMatchInIpTosBits {
          type binary {
            length "0..1";
          }
          description
           "Match incoming packet frame with specified IP TOS bits value.
            Empty string indicates that parameter has not been defined.";
          smiv2:defval "";
          smiv2:max-access read-write;
          smiv2:oid 1.3.6.1.4.1.1332.1.1.5.3.12.7.1.19;
        }

        leaf msanQosProfileMatchInIpTosMask {
          type binary {
            length "0..1";
          }
          description
           "This mask value identifies the portion of msanQosProfileMatchInIpTosBits that
            is compared against a packet.
            Empty string indicates that parameter has not been defined.";
          smiv2:defval "";
          smiv2:max-access read-write;
          smiv2:oid 1.3.6.1.4.1.1332.1.1.5.3.12.7.1.20;
        }

        leaf msanQosProfileMatchInL4SrcPort {
          type int32 {
            range "-1..65535";
          }
          description
           "Match incoming packet frame with specified source TCP/UDP port number.
            A value of -1 indicates that parameter has not been defined.";
          smiv2:defval -1;
          smiv2:max-access read-write;
          smiv2:oid 1.3.6.1.4.1.1332.1.1.5.3.12.7.1.21;
        }

        leaf msanQosProfileMatchInL4DestPort {
          type int32 {
            range "-1..65535";
          }
          description
           "Match incoming packet frame with specified destination TCP/UDP port number in downstream direction.
            A value of -1 indicates that parameter has not been defined.";
          smiv2:defval -1;
          smiv2:max-access read-write;
          smiv2:oid 1.3.6.1.4.1.1332.1.1.5.3.12.7.1.22;
        }

        leaf msanQosProfileMatchOutAny {
          type enumeration {
            enum enable {
              value 1;
            }
            enum disable {
              value 2;
            }
          }
          description
           "Match every outgoing packet frame in upstream direction.";
          smiv2:defval disable;
          smiv2:max-access read-write;
          smiv2:oid 1.3.6.1.4.1.1332.1.1.5.3.12.7.1.23;
        }

        leaf msanQosProfileMatchOutMacDestAddr {
          type yang:mac-address;
          description
           "Match outgoing packet frame with specified destination MAC address.
            Empty string indicates that parameter has not been defined";
          smiv2:defval "";
          smiv2:max-access read-write;
          smiv2:oid 1.3.6.1.4.1.1332.1.1.5.3.12.7.1.24;
        }

        leaf msanQosProfileMatchOutMacDestMask {
          type yang:mac-address;
          description
           "This mask value identifies the portion of msanQosProfileMatchOutMacDestAddr that
            is compared with output packet.
            Empty string indicates that parameter has not been defined";
          smiv2:defval "";
          smiv2:max-access read-write;
          smiv2:oid 1.3.6.1.4.1.1332.1.1.5.3.12.7.1.25;
        }

        leaf msanQosProfileMatchOutMacSrcAddr {
          type yang:mac-address;
          description
           "Match outgoing packet frame with specified source MAC address.
            Empty string indicates that parameter has not been defined";
          smiv2:defval "";
          smiv2:max-access read-write;
          smiv2:oid 1.3.6.1.4.1.1332.1.1.5.3.12.7.1.26;
        }

        leaf msanQosProfileMatchOutMacSrcMask {
          type yang:mac-address;
          description
           "This mask value identifies the portion of msanQosProfileMatchOutMacSrcAddr that
            is compared with output packet.
            Empty string indicates that parameter has not been defined";
          smiv2:defval "";
          smiv2:max-access read-write;
          smiv2:oid 1.3.6.1.4.1.1332.1.1.5.3.12.7.1.27;
        }

        leaf msanQosProfileMatchOutCos {
          type int32 {
            range "-1..7";
          }
          description
           "Match outgoing packet frame with specified CoS value (0-7).
            A value of -1 indicates that parameter has not been defined";
          smiv2:defval -1;
          smiv2:max-access read-write;
          smiv2:oid 1.3.6.1.4.1.1332.1.1.5.3.12.7.1.28;
        }

        leaf msanQosProfileMatchOutCos2 {
          type int32 {
            range "-1..7";
          }
          description
           "Match outgoing packet frame with specified secondary (C-TAG) CoS value (0-7).
            A value of -1 indicates that parameter has not been defined";
          smiv2:defval -1;
          smiv2:max-access read-write;
          smiv2:oid 1.3.6.1.4.1.1332.1.1.5.3.12.7.1.29;
        }

        leaf msanQosProfileMatchOutVlanId {
          type int32 {
            range "-1..4094";
          }
          description
           "Match outgoing packet frame with specified VLAN ID value (1-4094).
            A value of -1 indicates that parameter has not been defined";
          smiv2:defval -1;
          smiv2:max-access read-write;
          smiv2:oid 1.3.6.1.4.1.1332.1.1.5.3.12.7.1.30;
        }

        leaf msanQosProfileMatchOutVlanId2 {
          type int32 {
            range "-1..4094";
          }
          description
           "Match outgoing packet frame with specified secondary (C-TAG) VLAN ID value (1-4094).
            A value of -1 indicates that parameter has not been defined";
          smiv2:defval -1;
          smiv2:max-access read-write;
          smiv2:oid 1.3.6.1.4.1.1332.1.1.5.3.12.7.1.31;
        }

        leaf msanQosProfileMatchOutEthertype {
          type int32 {
            range "-1..65535";
          }
          description
           "Match outgoing packet frame with specified EtherType value.
            A value of -1 indicates that parameter has not been defined.";
          smiv2:defval -1;
          smiv2:max-access read-write;
          smiv2:oid 1.3.6.1.4.1.1332.1.1.5.3.12.7.1.32;
        }

        leaf msanQosProfileMatchOutIpProtocol {
          type int32 {
            range "-1..255";
          }
          description
           "Match outgoing packet frame with specified IP protocol value in upstream direction.
            A value of -1 indicates that parameter has not been defined.
            Some of standard protocol values:
               icmp - 1
               igmp - 2
               ip - 4 (ip in ip encapsulation)
               tcp - 6
               udp - 17";
          smiv2:defval -1;
          smiv2:max-access read-write;
          smiv2:oid 1.3.6.1.4.1.1332.1.1.5.3.12.7.1.33;
        }

        leaf msanQosProfileMatchOutIpSrcAddr {
          type inet:ipv4-address;
          description
           "Match outgoing packet frame with specified source IP address.
            Empty string indicates that parameter has not been defined.";
          smiv2:defval "";
          smiv2:max-access read-write;
          smiv2:oid 1.3.6.1.4.1.1332.1.1.5.3.12.7.1.34;
        }

        leaf msanQosProfileMatchOutIpSrcMask {
          type inet:ipv4-address;
          description
           "This mask value identifies the portion of msanQosProfileMatchOutIpSrcAddr that
            is compared with output packet.
            Empty string indicates that parameter has not been defined";
          smiv2:defval "";
          smiv2:max-access read-write;
          smiv2:oid 1.3.6.1.4.1.1332.1.1.5.3.12.7.1.35;
        }

        leaf msanQosProfileMatchOutIpDestAddr {
          type inet:ipv4-address;
          description
           "Match outgoing packet frame with specified destination IP address.
            Empty string indicates that parameter has not been defined.";
          smiv2:defval "";
          smiv2:max-access read-write;
          smiv2:oid 1.3.6.1.4.1.1332.1.1.5.3.12.7.1.36;
        }

        leaf msanQosProfileMatchOutIpDestMask {
          type inet:ipv4-address;
          description
           "This mask value identifies the portion of msanQosProfileMatchOutIpDestAddr that
            is compared with output packet.
            Empty string indicates that parameter has not been defined";
          smiv2:defval "";
          smiv2:max-access read-write;
          smiv2:oid 1.3.6.1.4.1.1332.1.1.5.3.12.7.1.37;
        }

        leaf msanQosProfileMatchOutIpDscp {
          type int32 {
            range "-1..63";
          }
          description
           "Match outgoing packet frame with specified IP DSCP value.
            A value of -1 indicates that parameter has not been defined.";
          smiv2:defval -1;
          smiv2:max-access read-write;
          smiv2:oid 1.3.6.1.4.1.1332.1.1.5.3.12.7.1.38;
        }

        leaf msanQosProfileMatchOutIpPrecedence {
          type int32 {
            range "-1..7";
          }
          description
           "Match outgoing packet frame with specified IP precedence (part of TOS field) value.
            A value of -1 indicates that parameter has not been defined.";
          smiv2:defval -1;
          smiv2:max-access read-write;
          smiv2:oid 1.3.6.1.4.1.1332.1.1.5.3.12.7.1.39;
        }

        leaf msanQosProfileMatchOutIpTosBits {
          type binary {
            length "0..1";
          }
          description
           "Match outgoing packet frame with specified IP TOS bits value.
            Empty string indicates that parameter has not been defined.";
          smiv2:defval "";
          smiv2:max-access read-write;
          smiv2:oid 1.3.6.1.4.1.1332.1.1.5.3.12.7.1.40;
        }

        leaf msanQosProfileMatchOutIpTosMask {
          type binary {
            length "0..1";
          }
          description
           "This mask value identifies the portion of msanQosProfileMatchOutIpTosBits that
            is compared with output packet.
            Empty string indicates that parameter has not been defined";
          smiv2:defval "";
          smiv2:max-access read-write;
          smiv2:oid 1.3.6.1.4.1.1332.1.1.5.3.12.7.1.41;
        }

        leaf msanQosProfileMatchOutL4SrcPort {
          type int32 {
            range "-1..65535";
          }
          description
           "Match outgoing packet frame with specified source TCP/UDP port number in upstream direction.
            A value of -1 indicates that parameter has not been defined.";
          smiv2:defval -1;
          smiv2:max-access read-write;
          smiv2:oid 1.3.6.1.4.1.1332.1.1.5.3.12.7.1.42;
        }

        leaf msanQosProfileMatchOutL4DestPort {
          type int32 {
            range "-1..65535";
          }
          description
           "Match outgoing packet frame with specified destination TCP/UDP port number.
            A value of -1 indicates that parameter has not been defined.";
          smiv2:defval -1;
          smiv2:max-access read-write;
          smiv2:oid 1.3.6.1.4.1.1332.1.1.5.3.12.7.1.43;
        }

        leaf msanQosProfileInCdr {
          type int32 {
            range "-1..1000000";
          }
          units kbps;
          description
           "Incoming committed data rate (E-CDR) in kbps (0 � 1000000).
            A value of -1 indicates that parameter has not been defined.";
          smiv2:defval 0;
          smiv2:max-access read-write;
          smiv2:oid 1.3.6.1.4.1.1332.1.1.5.3.12.7.1.44;
        }

        leaf msanQosProfileInPdr {
          type int32 {
            range "-1..1000000";
          }
          units kbps;
          description
           "Incoming peak data rate (E-PDR) in kbps (0 � 1000000).
            A value of -1 indicates that parameter has not been defined.";
          smiv2:defval 0;
          smiv2:max-access read-write;
          smiv2:oid 1.3.6.1.4.1.1332.1.1.5.3.12.7.1.45;
        }

        leaf msanQosProfileOutCdr {
          type int32 {
            range "-1..1000000";
          }
          units kbps;
          description
           "Outgoing committed data rate (E-CDR) in kbps (0 � 1000000).
            A value of -1 indicates that parameter has not been defined.";
          smiv2:defval 0;
          smiv2:max-access read-write;
          smiv2:oid 1.3.6.1.4.1.1332.1.1.5.3.12.7.1.46;
        }

        leaf msanQosProfileOutPdr {
          type int32 {
            range "-1..1000000";
          }
          units kbps;
          description
           "Outgoing peak data rate (E-PDR) in kbps (0 � 1000000).
            A value of -1 indicates that parameter has not been defined.";
          smiv2:defval 0;
          smiv2:max-access read-write;
          smiv2:oid 1.3.6.1.4.1.1332.1.1.5.3.12.7.1.47;
        }

        leaf msanQosProfileInTrustMode {
          type enumeration {
            enum untrusted {
              value 1;
            }
            enum trustCos {
              value 2;
            }
            enum trustDscp {
              value 3;
            }
            enum untrustMarkCos {
              value 4;
            }
            enum untrustMarkDscp {
              value 5;
            }
          }
          description
           "Trust mode for incoming packets which correspond to this profile.
            Default value is untrusted(1).
            
            Value untrustMarkCos(4) can be set if parameter msanQosProfileInMarkCos value
            is grater than -1.
            Value untrustMarkCos(5) can be set if parameter msanQosProfileInMarkDscp value
            is grater than -1.";
          smiv2:defval untrusted;
          smiv2:max-access read-write;
          smiv2:oid 1.3.6.1.4.1.1332.1.1.5.3.12.7.1.48;
        }

        leaf msanQosProfileInMarkCos {
          type int32 {
            range "-1..7";
          }
          description
           "Mark incoming packets with specified CoS value (0-7).
            A value of -1 indicates that parameter has not been defined";
          smiv2:defval -1;
          smiv2:max-access read-write;
          smiv2:oid 1.3.6.1.4.1.1332.1.1.5.3.12.7.1.49;
        }

        leaf msanQosProfileInMarkDscp {
          type int32 {
            range "-1..63";
          }
          description
           "Mark incoming packets with specified IP DSCP value.
            A value of -1 indicates that parameter has not been defined.";
          smiv2:defval -1;
          smiv2:max-access read-write;
          smiv2:oid 1.3.6.1.4.1.1332.1.1.5.3.12.7.1.50;
        }

        leaf msanQosProfileRowStatus {
          type snmpv2-tc:RowStatus;
          description
           "The row status object controls the creation/deletion of rows in this table.
            Its semantics are the same as those for the RowStatus textual convention specified for SNMPv2.
            For row creation use createAndWait(5).
            Value active(1) will activate and value destroy(6) will remove this entry.
            Other values are currently not supported.";
          smiv2:max-access read-write;
          smiv2:oid 1.3.6.1.4.1.1332.1.1.5.3.12.7.1.51;
        }

        leaf msanQosProfilePriority {
          type enumeration {
            enum normal {
              value 1;
            }
            enum high {
              value 2;
            }
          }
          description
           "Priority of QoS profile.
            On interface can be linked only one QoS profile
            with high(2) prority (msanQoSIntProfileTable)";
          smiv2:defval normal;
          smiv2:max-access read-write;
          smiv2:oid 1.3.6.1.4.1.1332.1.1.5.3.12.7.1.52;
        }

        leaf msanQosProfileInCdrBurstSize {
          type int32;
          units kB;
          description
           "Incoming committed data rate burst size in kB (0 � 16384).
            
            When parameter is set to 0 (default), it's automatically updated to default
            burst size in according with current msanQoSProfileInCdr value.";
          smiv2:max-access read-write;
          smiv2:oid 1.3.6.1.4.1.1332.1.1.5.3.12.7.1.53;
        }

        leaf msanQosProfileInPdrBurstSize {
          type int32;
          units kB;
          description
           "Incoming peak data rate burst size in kB (0 � 16384).
            
            When parameter is set to 0 (default), it's automatically updated to default
            burst size in according with current msanQoSProfileInPdr value.";
          smiv2:max-access read-write;
          smiv2:oid 1.3.6.1.4.1.1332.1.1.5.3.12.7.1.54;
        }

        leaf msanQosProfileOutCdrBurstSize {
          type int32;
          units kB;
          description
           "Outgoing committed data rate burst size in kB (0 � 16384).
            
            When parameter is set to 0 (default), it's automatically updated to default
            burst size in according with current msanQoSProfileOutCdr value.";
          smiv2:max-access read-write;
          smiv2:oid 1.3.6.1.4.1.1332.1.1.5.3.12.7.1.55;
        }

        leaf msanQosProfileOutPdrBurstSize {
          type int32;
          units kB;
          description
           "Outgoing peak data rate burst size in kB (0 � 16384).
            
            
            When parameter is set to 0 (default), it's automatically updated to default
            burst size in according with current msanQoSProfileOutCdr value.";
          smiv2:defval 64;
          smiv2:max-access read-write;
          smiv2:oid 1.3.6.1.4.1.1332.1.1.5.3.12.7.1.56;
        }

        leaf msanQosProfileMatchInSrcIpv6Address {
          type inet-address:InetAddressIPv6;
          description
           "Match incoming packet frame with specified source IPv6 address.
            
            Empty string indicates that parameter has not been defined.";
          smiv2:max-access read-write;
          smiv2:oid 1.3.6.1.4.1.1332.1.1.5.3.12.7.1.58;
        }

        leaf msanQosProfileMatchInSrcIpv6AddressMaskLen {
          type int32 {
            range "0..128";
          }
          description
           "The length of the prefix (in bits) associated with the
            incoming IPv6 source address of this entry (msanQosProfileMatchInSrcIpv6Address).
            
            Value 0 indicates that parameter has not been defined.";
          smiv2:defval 0;
          smiv2:max-access read-write;
          smiv2:oid 1.3.6.1.4.1.1332.1.1.5.3.12.7.1.59;
        }

        leaf msanQosProfileMatchInDestIpv6Address {
          type inet-address:InetAddressIPv6;
          description
           "Match incoming packet frame with specified destination IPv6 address.
            
            Empty string indicates that parameter has not been defined.";
          smiv2:max-access read-write;
          smiv2:oid 1.3.6.1.4.1.1332.1.1.5.3.12.7.1.60;
        }

        leaf msanQosProfileMatchInDestIpv6AddressMaskLen {
          type int32 {
            range "0..128";
          }
          description
           "The length of the prefix (in bits) associated with the
            incoming IPv6 destination address of this entry (msanQosProfileMatchInDestIpv6Address).
            
            Value 0 indicates that parameter has not been defined.";
          smiv2:defval 0;
          smiv2:max-access read-write;
          smiv2:oid 1.3.6.1.4.1.1332.1.1.5.3.12.7.1.61;
        }

        leaf msanQosProfileMatchOutSrcIpv6Address {
          type inet-address:InetAddressIPv6;
          description
           "Match outgoing packet frame with specified source IPv6 address.
            
            Empty string indicates that parameter has not been defined.";
          smiv2:max-access read-write;
          smiv2:oid 1.3.6.1.4.1.1332.1.1.5.3.12.7.1.63;
        }

        leaf msanQosProfileMatchOutSrcIpv6AddressMaskLen {
          type int32 {
            range "0..128";
          }
          description
           "The length of the prefix (in bits) associated with the
            outcoming IPv6 source address of this entry (msanQosProfileMatchOutSrcIpv6Address).
            
            Value 0 indicates that parameter has not been defined.";
          smiv2:defval 0;
          smiv2:max-access read-write;
          smiv2:oid 1.3.6.1.4.1.1332.1.1.5.3.12.7.1.64;
        }

        leaf msanQosProfileMatchOutDestIpv6Address {
          type inet-address:InetAddressIPv6;
          description
           "Match outcoming packet frame with specified destination IPv6 address.
            
            Empty string indicates that parameter has not been defined.";
          smiv2:max-access read-write;
          smiv2:oid 1.3.6.1.4.1.1332.1.1.5.3.12.7.1.65;
        }

        leaf msanQosProfileMatchOutDestIpv6AddressMaskLen {
          type int32 {
            range "0..128";
          }
          description
           "The length of the prefix (in bits) associated with the
            outcoming IPv6 destination address of this entry (msanQosProfileMatchOutDestIpv6Address).
            
            Value 0 indicates that parameter has not been defined.";
          smiv2:defval 0;
          smiv2:max-access read-write;
          smiv2:oid 1.3.6.1.4.1.1332.1.1.5.3.12.7.1.66;
        }
      }
    }

    container msanQosIntfProfileTable {
      description
       "This table connects selected QoS profiles (msanQoSProfileName) to specified interfaces (ifIndex).";
      smiv2:oid 1.3.6.1.4.1.1332.1.1.5.3.12.8;

      list msanQosIntfProfileEntry {
        key "ifIndex msanQosProfileName";
        description
         "Description.";
        smiv2:oid 1.3.6.1.4.1.1332.1.1.5.3.12.8.1;

        leaf ifIndex {
          type leafref {
            path "/if-mib:interfaces/if-mib:ifEntry/if-mib:ifIndex";
          }
        }

        leaf msanQosProfileName {
          type leafref {
            path "/iskratel-msan:ISKRATEL-MSAN-MIB/iskratel-msan:msanQosProfileTable/iskratel-msan:msanQosProfileEntry/iskratel-msan:msanQosProfileName";
          }
        }

        leaf msanQosIntfProfileAtmVpi {
          type int32 {
            range "-1..65535";
          }
          description
           "ATM Virtual path identifier of the ADSL interface.
            Value -1 indicates that parameter has not been defined.";
          smiv2:defval -1;
          smiv2:max-access read-write;
          smiv2:oid 1.3.6.1.4.1.1332.1.1.5.3.12.8.1.1;
        }

        leaf msanQosIntfProfileAtmVci {
          type int32 {
            range "-1..65535";
          }
          description
           "ATM Virtual channel identifier of the ADSL interface.
            Value -1 indicates that parameter has not been defined.";
          smiv2:defval -1;
          smiv2:max-access read-write;
          smiv2:oid 1.3.6.1.4.1.1332.1.1.5.3.12.8.1.2;
        }

        leaf msanQosIntfProfileRowStatus {
          type snmpv2-tc:RowStatus;
          description
           "The row status object controls the creation/deletion of rows in this table.
            Its semantics are the same as those for the RowStatus textual convention specified for SNMPv2.
            For row creation use createAndWait(5).
            For row activation use active(1).
            For row deactivation use notInService(2).
            For row deletion use destroy(6).
            
            Other values are currently not supported.
            
            On interface can be linked only one QoS profile with high(2) prority (msanQosProfilePriority)";
          smiv2:max-access read-write;
          smiv2:oid 1.3.6.1.4.1.1332.1.1.5.3.12.8.1.3;
        }
      }
    }

    container msanQosPortStatTable {
      description
       "Description.";
      smiv2:oid 1.3.6.1.4.1.1332.1.1.5.3.12.9.1;

      list msanQosPortStatEntry {
        key ifIndex;
        description
         "Description.";
        smiv2:oid 1.3.6.1.4.1.1332.1.1.5.3.12.9.1.1;

        leaf ifIndex {
          type leafref {
            path "/if-mib:interfaces/if-mib:ifEntry/if-mib:ifIndex";
          }
        }

        leaf msanQosPortStatInDroppedFrames {
          type yang:counter32;
          description
           "Number of dropped frames per port in incoming direction.";
          smiv2:max-access read-only;
          smiv2:oid 1.3.6.1.4.1.1332.1.1.5.3.12.9.1.1.1;
        }

        leaf msanQosPortStatOutDroppedFrames {
          type yang:counter32;
          description
           "Number of dropped frames per port in outgoing direction.";
          smiv2:max-access read-only;
          smiv2:oid 1.3.6.1.4.1.1332.1.1.5.3.12.9.1.1.2;
        }
      }
    }

    container msanQosPortProfileStatTable {
      description
       "Description.";
      smiv2:oid 1.3.6.1.4.1.1332.1.1.5.3.12.9.2;

      list msanQosPortProfileStatEntry {
        key "ifIndex msanQosProfileName";
        description
         "Description.";
        smiv2:oid 1.3.6.1.4.1.1332.1.1.5.3.12.9.2.1;

        leaf ifIndex {
          type leafref {
            path "/if-mib:interfaces/if-mib:ifEntry/if-mib:ifIndex";
          }
        }

        leaf msanQosProfileName {
          type leafref {
            path "/iskratel-msan:ISKRATEL-MSAN-MIB/iskratel-msan:msanQosProfileTable/iskratel-msan:msanQosProfileEntry/iskratel-msan:msanQosProfileName";
          }
        }

        leaf msanQosPortProfileStatQueueCurrent {
          type int32;
          description
           "Current queue occupation per profile per port (in number of packets) .";
          smiv2:max-access read-only;
          smiv2:oid 1.3.6.1.4.1.1332.1.1.5.3.12.9.2.1.1;
        }

        leaf msanQosPortProfileStatQueueAverage {
          type int32;
          description
           "Average queue occupation per profile per port (in number of packets) .";
          smiv2:max-access read-only;
          smiv2:oid 1.3.6.1.4.1.1332.1.1.5.3.12.9.2.1.2;
        }

        leaf msanQosPortProfileStatQueueMax {
          type int32;
          description
           "Maximum queue occupation per profile per port (in number of packets) .";
          smiv2:max-access read-only;
          smiv2:oid 1.3.6.1.4.1.1332.1.1.5.3.12.9.2.1.3;
        }
      }
    }

    container msanIpAclTable {
      description
       "Description.";
      smiv2:oid 1.3.6.1.4.1.1332.1.1.5.3.12.10;

      list msanIpAclEntry {
        key msanIpAclId;
        description
         "Description.";
        smiv2:oid 1.3.6.1.4.1.1332.1.1.5.3.12.10.1;

        leaf msanIpAclId {
          type int32 {
            range "1..199";
          }
          description
           "This is aclIndex in aclTable (1.3.6.1.4.1.1332.1.1.5.2.3.2.1)";
          smiv2:max-access not-accessible;
          smiv2:oid 1.3.6.1.4.1.1332.1.1.5.3.12.10.1.1;
        }

        leaf msanIpAclProtection {
          type enumeration {
            enum unprotected {
              value 0;
            }
            enum protected {
              value 1;
            }
          }
          description
           "If protection flag is set to protected (1), other profile values cannot be edited.
            
            Protection flag is always  protected (1) and it can't be changed if  profile is assigned as dynamic:
            msanAclProfileStatus = dynamic(2)";
          smiv2:defval unprotected;
          smiv2:max-access read-write;
          smiv2:oid 1.3.6.1.4.1.1332.1.1.5.3.12.10.1.2;
        }

        leaf msanIpAclStatus {
          type enumeration {
            enum static {
              value 1;
            }
            enum dynamic {
              value 2;
            }
          }
          description
           "Profile status.
            If status is dynamic, profile values can't be edited.";
          smiv2:max-access read-only;
          smiv2:oid 1.3.6.1.4.1.1332.1.1.5.3.12.10.1.4;
        }
      }
    }

    container msanMacAclTable {
      description
       "Description.";
      smiv2:oid 1.3.6.1.4.1.1332.1.1.5.3.12.11;

      list msanMacAclEntry {
        key msanMacAclId;
        description
         "Description.";
        smiv2:oid 1.3.6.1.4.1.1332.1.1.5.3.12.11.1;

        leaf msanMacAclId {
          type int32 {
            range "1..199";
          }
          description
           "This is aclMacIndex in aclMacTable (1.3.6.1.4.1.1332.1.1.5.2.3.2.6)";
          smiv2:max-access not-accessible;
          smiv2:oid 1.3.6.1.4.1.1332.1.1.5.3.12.11.1.1;
        }

        leaf msanMacAclProtection {
          type enumeration {
            enum unprotected {
              value 0;
            }
            enum protected {
              value 1;
            }
          }
          description
           "If protection flag is set to protected (1), other profile values cannot be edited.
            
            Protection flag is always  protected (1) and it can't be changed if  profile is assigned as dynamic:
            msanMacAclStatus = dynamic(2)";
          smiv2:defval unprotected;
          smiv2:max-access read-write;
          smiv2:oid 1.3.6.1.4.1.1332.1.1.5.3.12.11.1.3;
        }

        leaf msanMacAclStatus {
          type enumeration {
            enum static {
              value 1;
            }
            enum dynamic {
              value 2;
            }
          }
          description
           "Profile status.
            If status is dynamic, profile values can't be edited.";
          smiv2:max-access read-only;
          smiv2:oid 1.3.6.1.4.1.1332.1.1.5.3.12.11.1.4;
        }
      }
    }

    container msanDiagnosticsTestTable {
      description
       "Description.";
      smiv2:oid 1.3.6.1.4.1.1332.1.1.5.3.14.2;

      list msanDiagnosticsTestEntry {
        key msanDiagnosticsTestCode;
        description
         "Description.";
        smiv2:oid 1.3.6.1.4.1.1332.1.1.5.3.14.2.1;

        leaf msanDiagnosticsTestCode {
          type int32 {
            range "0..99999999";
          }
          description
           "Unique identification of a test program.";
          smiv2:max-access not-accessible;
          smiv2:oid 1.3.6.1.4.1.1332.1.1.5.3.14.2.1.1;
        }

        leaf msanDiagnosticsTestName {
          type binary;
          description
           "The name of a test program.";
          smiv2:max-access read-only;
          smiv2:oid 1.3.6.1.4.1.1332.1.1.5.3.14.2.1.2;
        }

        leaf msanDiagnosticsTestActivity {
          type enumeration {
            enum testOn {
              value 1;
            }
            enum testOff {
              value 2;
            }
          }
          description
           "Specifies the Test activity parameter for the diagnostic. ";
          smiv2:max-access read-write;
          smiv2:oid 1.3.6.1.4.1.1332.1.1.5.3.14.2.1.3;
        }

        leaf msanDiagnosticsTestTime {
          type uint32 {
            range "100..999999900";
          }
          description
           "Test time, whose interpretation depends on test running mode:
            
            - for cyclical tests, it means the period at which the test is
              carried out one after another (time unit is milisecond)
            
            - for all others, it means time of day in the form 'hhmmss'
              (e.g. '224950') at which the test begins.";
          smiv2:max-access read-write;
          smiv2:oid 1.3.6.1.4.1.1332.1.1.5.3.14.2.1.4;
        }

        leaf msanDiagnosticsTestPriority {
          type enumeration {
            enum low {
              value 0;
            }
            enum medium {
              value 1;
            }
            enum high {
              value 2;
            }
            enum veryHigh {
              value 3;
            }
          }
          description
           "Test priority parameter for the diagnostic.";
          smiv2:max-access read-write;
          smiv2:oid 1.3.6.1.4.1.1332.1.1.5.3.14.2.1.6;
        }

        leaf msanDiagnosticsTestType {
          type enumeration {
            enum testAtReload {
              value 1;
            }
            enum testPeriodically {
              value 2;
            }
            enum testDaily {
              value 3;
            }
          }
          description
           "
            Type of starting the test.
            
            DECIMAL VALUE   DESCRIPTION
                  1	        At start-up & Recovery
                  2	        Periodical
                  3	        Daily ";
          smiv2:max-access read-only;
          smiv2:oid 1.3.6.1.4.1.1332.1.1.5.3.14.2.1.7;
        }

        leaf msanDiagnosticsTestTimeMin {
          type int32;
          description
           "Minimum possible value of parameter msanDiagnosticTestTime.";
          smiv2:max-access read-only;
          smiv2:oid 1.3.6.1.4.1.1332.1.1.5.3.14.2.1.8;
        }

        leaf msanDiagnosticsTestTimeMax {
          type int32;
          description
           "Maximum possible value of parameter msanDiagnosticTestTime.";
          smiv2:max-access read-only;
          smiv2:oid 1.3.6.1.4.1.1332.1.1.5.3.14.2.1.9;
        }
      }
    }

    container msanDiagnosticsErrorTable {
      description
       "Description.";
      smiv2:oid 1.3.6.1.4.1.1332.1.1.5.3.14.3;

      list msanDiagnosticsErrorEntry {
        key msanDiagnosticsErrorCode;
        description
         "Description.";
        smiv2:oid 1.3.6.1.4.1.1332.1.1.5.3.14.3.1;

        leaf msanDiagnosticsErrorCode {
          type int32 {
            range "0..99999999";
          }
          description
           "Unique identification of an error reported during testing an object.";
          smiv2:max-access not-accessible;
          smiv2:oid 1.3.6.1.4.1.1332.1.1.5.3.14.3.1.1;
        }

        leaf msanDiagnosticsErrorDescription {
          type binary;
          description
           "Description of the error code.";
          smiv2:max-access read-only;
          smiv2:oid 1.3.6.1.4.1.1332.1.1.5.3.14.3.1.2;
        }

        leaf msanDiagnosticsErrorPriority {
          type enumeration {
            enum critical {
              value 1;
            }
            enum major {
              value 2;
            }
            enum minor {
              value 3;
            }
            enum warning {
              value 4;
            }
          }
          description
           "Error priority.";
          smiv2:max-access read-write;
          smiv2:oid 1.3.6.1.4.1.1332.1.1.5.3.14.3.1.3;
        }

        leaf msanDiagnosticsErrorObjectType {
          type binary;
          description
           "Object type - List of values can be found in alr_def.h";
          smiv2:max-access read-only;
          smiv2:oid 1.3.6.1.4.1.1332.1.1.5.3.14.3.1.4;
        }

        leaf msanDiagnosticsErrorMeasure {
          type binary;
          description
           "Measure (what is done when an error occurs, for instance reset the node, ...) - List of values can be found in alr_def.h";
          smiv2:max-access read-only;
          smiv2:oid 1.3.6.1.4.1.1332.1.1.5.3.14.3.1.5;
        }

        leaf msanDiagnosticsErrorMeasureActive {
          type enumeration {
            enum notActive {
              value 0;
            }
            enum active {
              value 1;
            }
          }
          description
           "Activity of measure. With setting this parameter to notActive(0), you can prevent excecution of measure.";
          smiv2:defval active;
          smiv2:max-access read-write;
          smiv2:oid 1.3.6.1.4.1.1332.1.1.5.3.14.3.1.6;
        }

        leaf msanDiagnosticsErrorProbableCause {
          type int32;
          description
           "Probable cause.";
          smiv2:max-access read-only;
          smiv2:oid 1.3.6.1.4.1.1332.1.1.5.3.14.3.1.7;
        }

        leaf msanDiagnosticsErrorObjectTypeId {
          type int32;
          description
           "Object type ID- List of values can be found in alr_def.h";
          smiv2:max-access read-only;
          smiv2:oid 1.3.6.1.4.1.1332.1.1.5.3.14.3.1.8;
        }

        leaf msanDiagnosticsErrorMeasureId {
          type int32;
          description
           "Measure (what is done when an error occurs, for instance reset the node, ...) - List of values can be found in alr_def.h";
          smiv2:max-access read-only;
          smiv2:oid 1.3.6.1.4.1.1332.1.1.5.3.14.3.1.9;
        }
      }
    }

    container msanDiagnosticsTempTable {
            config false;

      description
       "Description.";
      smiv2:oid 1.3.6.1.4.1.1332.1.1.5.3.14.4;

      list msanDiagnosticsTempEntry {
        key msanDiagnosticsTempSensorID;
        description
         "Description.";
        smiv2:oid 1.3.6.1.4.1.1332.1.1.5.3.14.4.1;

        leaf msanDiagnosticsTempSensorID {
          type int32 {
            range "0..100";
          }
          description
           "Temperature sensor ID.";
          smiv2:max-access not-accessible;
          smiv2:oid 1.3.6.1.4.1.1332.1.1.5.3.14.4.1.1;
        }

        leaf msanDiagnosticsTempSensorName {
          type binary;
          description
           "Temperature sensor name.";
          smiv2:max-access read-only;
          smiv2:oid 1.3.6.1.4.1.1332.1.1.5.3.14.4.1.2;
        }

        leaf msanDiagnosticsTempCurrent {
          type int32;
          description
           "Current temperature of the specified sensor in [deg C].";
          smiv2:max-access read-only;
          smiv2:oid 1.3.6.1.4.1.1332.1.1.5.3.14.4.1.3;
        }

        leaf msanDiagnosticsTempCriticUnderheatThreshold {
          type int32;
          description
           "Sensor critical underheat threshold temperature limit in [deg C].";
          smiv2:max-access read-only;
          smiv2:oid 1.3.6.1.4.1.1332.1.1.5.3.14.4.1.4;
        }

        leaf msanDiagnosticsTempUnderheatThreshold {
          type int32;
          description
           "Sensor underheat temperature threshold limit in [deg C].";
          smiv2:max-access read-only;
          smiv2:oid 1.3.6.1.4.1.1332.1.1.5.3.14.4.1.5;
        }

        leaf msanDiagnosticsTempOverheatThreshold {
          type int32;
          description
           "Sensor overheat threshold temperature limit in [deg C].";
          smiv2:max-access read-only;
          smiv2:oid 1.3.6.1.4.1.1332.1.1.5.3.14.4.1.6;
        }

        leaf msanDiagnosticsTempCriticOverheatThreshold {
          type int32;
          description
           "Sensor critical overheat threshold temperature limit in [deg C].";
          smiv2:max-access read-only;
          smiv2:oid 1.3.6.1.4.1.1332.1.1.5.3.14.4.1.7;
        }
      }
    }

    container msanDiagnosticsErrorFilterTable {
      description
       "Description.";
      smiv2:oid 1.3.6.1.4.1.1332.1.1.5.3.14.5;

      list msanDiagnosticsErrorFilterEntry {
        key "msanDiagnosticsErrorFilterErrMask msanDiagnosticsErrorFilterObjMask";
        description
         "Description.";
        smiv2:oid 1.3.6.1.4.1.1332.1.1.5.3.14.5.1;

        leaf msanDiagnosticsErrorFilterErrMask {
          type binary {
            length "1..20";
          }
          description
           "Error code in ascii format. Regular expression describing one or more error codes.";
          smiv2:max-access not-accessible;
          smiv2:oid 1.3.6.1.4.1.1332.1.1.5.3.14.5.1.1;
        }

        leaf msanDiagnosticsErrorFilterObjMask {
          type binary {
            length "1..40";
          }
          description
           "Type of object, which alarming is filtered for. Regular expression describing one or more test objects. ";
          smiv2:max-access not-accessible;
          smiv2:oid 1.3.6.1.4.1.1332.1.1.5.3.14.5.1.2;
        }

        leaf msanDiagnosticsErrorFilterRowStatus {
          type snmpv2-tc:RowStatus;
          description
           "The row status object controls the creation/deletion of rows in this table. Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.14.5.1.3;
        }
      }
    }

    container msanDiagnosticsErrorSeverityTable {
      description
       "Description.";
      smiv2:oid 1.3.6.1.4.1.1332.1.1.5.3.14.6;

      list msanDiagnosticsErrorSeverityEntry {
        key "msanDiagnosticsErrorSeverityErrCode msanDiagnosticsErrorSeverityObjMask";
        description
         "Description.";
        smiv2:oid 1.3.6.1.4.1.1332.1.1.5.3.14.6.1;

        leaf msanDiagnosticsErrorSeverityErrCode {
          type int32;
          description
           "Unique identification of an error reported during testing an object.
            All error codes are stated in alr_def.h (KFMT)";
          smiv2:max-access not-accessible;
          smiv2:oid 1.3.6.1.4.1.1332.1.1.5.3.14.6.1.1;
        }

        leaf msanDiagnosticsErrorSeverityErrPriority {
          type enumeration {
            enum critical {
              value 1;
            }
            enum major {
              value 2;
            }
            enum minor {
              value 3;
            }
            enum warning {
              value 4;
            }
          }
          description
           "Priority of error. ";
          smiv2:max-access read-write;
          smiv2:oid 1.3.6.1.4.1.1332.1.1.5.3.14.6.1.2;
        }

        leaf msanDiagnosticsErrorSeverityObjMask {
          type binary {
            length "1..40";
          }
          description
           "Type of object, which alarming is filtered for. Regular expression describing one or more test objects. ";
          smiv2:max-access not-accessible;
          smiv2:oid 1.3.6.1.4.1.1332.1.1.5.3.14.6.1.3;
        }

        leaf msanDiagnosticsErrorSeverityRowStatus {
          type snmpv2-tc:RowStatus;
          description
           "The row status object controls the creation/deletion of rows in this table. Its semantics are the same as those for the RowStatus textual convention specified for SNMPv2.
            For row creation use createAndWait(5) [createAndGo(4) is not supported].";
          smiv2:max-access read-write;
          smiv2:oid 1.3.6.1.4.1.1332.1.1.5.3.14.6.1.4;
        }
      }
    }

container msanDiagnosticsExtAlrSensorTable {
      description
       "Description.";
      smiv2:oid 1.3.6.1.4.1.1332.1.1.5.3.14.7;

      list msanDiagnosticsExtAlrSensorEntry {
        key msanDiagnosticsExtAlrSensorName;
        description
         "Description.";
        smiv2:oid 1.3.6.1.4.1.1332.1.1.5.3.14.7.1;

        leaf msanDiagnosticsExtAlrSensorName {
          type rfc1213-mib:DisplayString;
          description
           "Description.";
          smiv2:max-access not-accessible;
          smiv2:oid 1.3.6.1.4.1.1332.1.1.5.3.14.7.1.1;
        }

        leaf msanDiagnosticsExtAlrSensorAlarm {
          type enumeration {
            enum enable {
              value 1;
            }
            enum disable {
              value 2;
            }
          }
          description
           "Description.";
          smiv2:max-access read-write;
          smiv2:oid 1.3.6.1.4.1.1332.1.1.5.3.14.7.1.2;
        }

        leaf msanDiagnosticsExtAlrSensorLogic {
          type enumeration {
            enum open {
              value 1;
            }
            enum close {
              value 2;
            }
          }
          description
           "Description.";
          smiv2:max-access read-write;
          smiv2:oid 1.3.6.1.4.1.1332.1.1.5.3.14.7.1.3;
        }
      }
    }


    container msanAlarmPanelTable {
      description
       "Description.";
      smiv2:oid 1.3.6.1.4.1.1332.1.1.5.3.16.2;

      list msanAlarmPanelEntry {
        key msanAlarmPanelIndex;
        description
         "Description.";
        smiv2:oid 1.3.6.1.4.1.1332.1.1.5.3.16.2.1;

        leaf msanAlarmPanelIndex {
          type int32 {
            range "1..16";
          }
          description
           "Unique identification of an alarm panel.";
          smiv2:max-access not-accessible;
          smiv2:oid 1.3.6.1.4.1.1332.1.1.5.3.16.2.1.1;
        }

        leaf msanAlarmPanelConnectionState {
          type enumeration {
            enum up {
              value 1;
            }
            enum down {
              value 2;
            }
          }
          description
           "Alarm panel connection status";
          smiv2:max-access read-only;
          smiv2:oid 1.3.6.1.4.1.1332.1.1.5.3.16.2.1.2;
        }

        leaf msanAlarmPanelAdminState {
          type enumeration {
            enum unequipped {
              value 0;
            }
            enum equipped {
              value 1;
            }
          }
          description
           "Flag determining whether an alarm panel is equipped or not.";
          smiv2:max-access read-write;
          smiv2:oid 1.3.6.1.4.1.1332.1.1.5.3.16.2.1.3;
        }
      }
    }

    container msanAlarmPanelIndicatorTable {
      description
       "Description.";
      smiv2:oid 1.3.6.1.4.1.1332.1.1.5.3.16.3;

      list msanAlarmPanelIndicatorEntry {
        key "msanAlarmPanelIndex msanAlarmPanelIndicatorIndex";
        description
         "Description.";
        smiv2:oid 1.3.6.1.4.1.1332.1.1.5.3.16.3.1;

        leaf msanAlarmPanelIndex {
          type leafref {
            path "/iskratel-msan:ISKRATEL-MSAN-MIB/iskratel-msan:msanAlarmPanelTable/iskratel-msan:msanAlarmPanelEntry/iskratel-msan:msanAlarmPanelIndex";
          }
        }

        leaf msanAlarmPanelIndicatorIndex {
          type int32 {
            range "1..15";
          }
          description
           "Alarm panel indicator number. ";
          smiv2:max-access not-accessible;
          smiv2:oid 1.3.6.1.4.1.1332.1.1.5.3.16.3.1.1;
        }

        leaf msanAlarmPanelIndicatorErrCode {
          type int32;
          description
           "Alarm panel indicator error number.";
          smiv2:max-access read-write;
          smiv2:oid 1.3.6.1.4.1.1332.1.1.5.3.16.3.1.2;
        }
      }
    }

    container msanAlarmPanelInputTable {
      description
       "Description.";
      smiv2:oid 1.3.6.1.4.1.1332.1.1.5.3.16.4;

      list msanAlarmPanelInputEntry {
        key "msanAlarmPanelIndex msanAlarmPanelInputIndex";
        description
         "Description.";
        smiv2:oid 1.3.6.1.4.1.1332.1.1.5.3.16.4.1;

        leaf msanAlarmPanelIndex {
          type leafref {
            path "/iskratel-msan:ISKRATEL-MSAN-MIB/iskratel-msan:msanAlarmPanelTable/iskratel-msan:msanAlarmPanelEntry/iskratel-msan:msanAlarmPanelIndex";
          }
        }

        leaf msanAlarmPanelInputIndex {
          type int32 {
            range "1..15";
          }
          description
           "Alarm panel input sensor number.";
          smiv2:max-access not-accessible;
          smiv2:oid 1.3.6.1.4.1.1332.1.1.5.3.16.4.1.1;
        }

        leaf msanAlarmPanelInputErrCode {
          type int32;
          description
           "Alarm panel input sensor error code.";
          smiv2:max-access read-write;
          smiv2:oid 1.3.6.1.4.1.1332.1.1.5.3.16.4.1.2;
        }

        leaf msanAlarmPanelInputActiveLevel {
          type enumeration {
            enum low {
              value 0;
            }
            enum high {
              value 1;
            }
          }
          description
           "Alarm panel input sensor active level.";
          smiv2:max-access read-write;
          smiv2:oid 1.3.6.1.4.1.1332.1.1.5.3.16.4.1.3;
        }
      }
    }

    container msanMvrPortTable {
      description
       "Description.";
      smiv2:oid 1.3.6.1.4.1.1332.1.1.5.3.17.2;

      list msanMvrPortEntry {
        key ifIndex;
        description
         "Description.";
        smiv2:oid 1.3.6.1.4.1.1332.1.1.5.3.17.2.1;

        leaf ifIndex {
          type leafref {
            path "/if-mib:interfaces/if-mib:ifEntry/if-mib:ifIndex";
          }
        }

        leaf msanMvrPortAdminMode {
          type enumeration {
            enum enable {
              value 1;
            }
            enum disable {
              value 2;
            }
          }
          description
           "Administrative mode for Multicast VLAN Registration (a.k.a. Service Based Tagging) for the selected interface";
          smiv2:max-access read-write;
          smiv2:oid 1.3.6.1.4.1.1332.1.1.5.3.17.2.1.1;
        }
      }
    }

    container msanMvrMulticastGroupTable {
      description
       "Description.";
      smiv2:oid 1.3.6.1.4.1.1332.1.1.5.3.17.3;

      list msanMvrMulticastGroupEntry {
        key "msanMvrMulticastGroupMVlanId msanMvrMulticastGroupStartIp";
        description
         "Description.";
        smiv2:oid 1.3.6.1.4.1.1332.1.1.5.3.17.3.1;

        leaf msanMvrMulticastGroupMVlanId {
          type int32;
          description
           "VLAN ID (refers to dot1qVlanIndex) where MVR functionality is used.";
          smiv2:max-access not-accessible;
          smiv2:oid 1.3.6.1.4.1.1332.1.1.5.3.17.3.1.1;
        }

        leaf msanMvrMulticastGroupStartIp {
          type inet:ipv4-address;
          description
           "Start IP Address of the multicast group range.";
          smiv2:max-access not-accessible;
          smiv2:oid 1.3.6.1.4.1.1332.1.1.5.3.17.3.1.2;
        }

        leaf msanMvrMulticastGroupEndIp {
          type inet:ipv4-address;
          description
           "End IP Address of the multicast group range.";
          smiv2:max-access read-write;
          smiv2:oid 1.3.6.1.4.1.1332.1.1.5.3.17.3.1.3;
        }

        leaf msanMvrMulticastGroupRowStatus {
          type snmpv2-tc:RowStatus;
          description
           "The row status object controls the creation/deletion of rows in this table.
            For row creation use createAndWait(5) [createAndGo(4) is not supported].";
          smiv2:max-access read-write;
          smiv2:oid 1.3.6.1.4.1.1332.1.1.5.3.17.3.1.4;
        }
      }
    }

    container msanMvrConfigTable {
      description
       "Description.";
      smiv2:oid 1.3.6.1.4.1.1332.1.1.5.3.17.4;

      list msanMvrConfigEntry {
        key "ifIndex msanMvrConfigCVlanId msanMvrConfigMVlanId";
        description
         "Description.";
        smiv2:oid 1.3.6.1.4.1.1332.1.1.5.3.17.4.1;

        leaf ifIndex {
          type leafref {
            path "/if-mib:interfaces/if-mib:ifEntry/if-mib:ifIndex";
          }
        }

        leaf msanMvrConfigCVlanId {
          type int32 {
            range "1..4094";
          }
          description
           "Customer VLAN ID for the selected interface from which
            IGMP Join/Leave messages will be remarked.";
          smiv2:max-access not-accessible;
          smiv2:oid 1.3.6.1.4.1.1332.1.1.5.3.17.4.1.1;
        }

        leaf msanMvrConfigMVlanId {
          type int32 {
            range "1..4092";
          }
          description
           "Service provider multicast VLAN ID for the selected interface
            to which IGMP Join/Leave messages will be remarked.";
          smiv2:max-access not-accessible;
          smiv2:oid 1.3.6.1.4.1.1332.1.1.5.3.17.4.1.2;
        }

        leaf msanMvrConfigCos {
          type int32 {
            range "-1..7";
          }
          description
           "Output CoS priority on the selected interface. IGMP messages received from
            this interface will have this priority when they are transmitted into service provider
            multicast VLAN.
            
            Value '-1' defines that original CoS value is not changed.";
          smiv2:defval 0;
          smiv2:max-access read-write;
          smiv2:oid 1.3.6.1.4.1.1332.1.1.5.3.17.4.1.3;
        }

        leaf msanMvrConfigRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.17.4.1.4;
        }
      }
    }

    container msanMvrDvlanTable {
      description
       "Description.";
      smiv2:oid 1.3.6.1.4.1.1332.1.1.5.3.17.5;

      list msanMvrDvlanEntry {
        key ifIndex;
        description
         "Description.";
        smiv2:oid 1.3.6.1.4.1.1332.1.1.5.3.17.5.1;

        leaf ifIndex {
          type leafref {
            path "/if-mib:interfaces/if-mib:ifEntry/if-mib:ifIndex";
          }
        }

        leaf msanMvrDvlanRmOuterTagStatus {
          type enumeration {
            enum enable {
              value 1;
            }
            enum disable {
              value 2;
            }
          }
          description
           "The desired state of removing outer tags on IGMP packets funcionality.";
          smiv2:defval disable;
          smiv2:max-access read-write;
          smiv2:oid 1.3.6.1.4.1.1332.1.1.5.3.17.5.1.1;
        }

        leaf msanMvrDvlanEthertypeRewriteStatus {
          type enumeration {
            enum enable {
              value 1;
            }
            enum disable {
              value 2;
            }
          }
          description
           "The desired state of rewriting ether type from outer vlan tag to inner vlan
            tag.";
          smiv2:defval disable;
          smiv2:max-access read-write;
          smiv2:oid 1.3.6.1.4.1.1332.1.1.5.3.17.5.1.2;
        }
      }
    }

    container msanRemoteAccessFilterTable {
      status deprecated;
      description
       "Description.";
      smiv2:oid 1.3.6.1.4.1.1332.1.1.5.3.18.2;

      list msanRemoteAccessFilterEntry {
        key msanRemoteAccessFilterRuleIndex;
        status deprecated;
        description
         "Description.";
        smiv2:oid 1.3.6.1.4.1.1332.1.1.5.3.18.2.1;

        leaf msanRemoteAccessFilterRuleIndex {
          type int32 {
            range "1..200";
          }
          status deprecated;
          description
           "Rule's index. Index should be continued, without gaps. ";
          smiv2:max-access not-accessible;
          smiv2:oid 1.3.6.1.4.1.1332.1.1.5.3.18.2.1.1;
        }

        leaf msanRemoteAccessFilterIp {
          type inet:ipv4-address;
          status deprecated;
          description
           "IP Address of the rule.";
          smiv2:max-access read-write;
          smiv2:oid 1.3.6.1.4.1.1332.1.1.5.3.18.2.1.2;
        }

        leaf msanRemoteAccessFilterNetmask {
          type inet:ipv4-address;
          status deprecated;
          description
           "Netmask of the rule.";
          smiv2:max-access read-write;
          smiv2:oid 1.3.6.1.4.1.1332.1.1.5.3.18.2.1.3;
        }

        leaf msanRemoteAccessFilterAction {
          type enumeration {
            enum accept {
              value 1;
            }
            enum deny {
              value 2;
            }
          }
          status deprecated;
          description
           "Action to be taken with a packet: accept or deny it.";
          smiv2:max-access read-write;
          smiv2:oid 1.3.6.1.4.1.1332.1.1.5.3.18.2.1.4;
        }

        leaf msanRemoteAccessFilterRowStatus {
          type snmpv2-tc:RowStatus;
          status deprecated;
          description
           "The row status object controls the creation/deletion of rows in this table.
            For row creation use createAndWait(5) [createAndGo(4) is not supported].";
          smiv2:max-access read-write;
          smiv2:oid 1.3.6.1.4.1.1332.1.1.5.3.18.2.1.5;
        }
      }
    }

    container msanDslSpecificTable {
      description
       "Description.";
      smiv2:oid 1.3.6.1.4.1.1332.1.1.5.3.19.3;

      list msanDslSpecificEntry {
        key ifIndex;
        description
         "Description.";
        smiv2:oid 1.3.6.1.4.1.1332.1.1.5.3.19.3.1;

        leaf ifIndex {
          type leafref {
            path "/if-mib:interfaces/if-mib:ifEntry/if-mib:ifIndex";
          }
        }

        leaf msanDslSpecificDsPsdMask {
          type binary;
          description
           "Unique name of the downstream PSD mask as defined by msanDslPsdMaskDsName.";
          smiv2:defval "";
          smiv2:max-access read-write;
          smiv2:oid 1.3.6.1.4.1.1332.1.1.5.3.19.3.1.1;
        }

        leaf msanDslSpecificUsPsdMask {
          type binary;
          description
           "Unique name of the upstream PSD mask as defined by msanDslPsdMaskUsName.";
          smiv2:defval ANSI_FTTCab_M11;
          smiv2:max-access read-write;
          smiv2:oid 1.3.6.1.4.1.1332.1.1.5.3.19.3.1.2;
        }

        leaf msanDslSpecificLineState {
          type enumeration {
            enum quiet {
              value 0;
            }
            enum idle {
              value 1;
            }
            enum activateInitTrain {
              value 2;
            }
            enum activeFullPower {
              value 3;
            }
            enum activeLowPower {
              value 4;
            }
            enum unitFail {
              value 5;
            }
            enum atpPtmLoopback {
              value 6;
            }
            enum dspDigitalLoopback {
              value 7;
            }
            enum lineDriverDigitalLoopback {
              value 8;
            }
            enum hybridLoopback {
              value 9;
            }
            enum testMode {
              value 10;
            }
            enum loopDiagnosticsDeltInit {
              value 11;
            }
            enum loopDiagnosticsDelt {
              value 12;
            }
            enum seltInits {
              value 13;
            }
            enum selt {
              value 14;
            }
            enum lowPowerL3 {
              value 15;
            }
          }
          description
           "VDSL system operational state. For normal blade operation this value should be active(3).
            If value is differ from 3, VDSL driver is not operational.";
          smiv2:max-access read-only;
          smiv2:oid 1.3.6.1.4.1.1332.1.1.5.3.19.3.1.3;
        }

        leaf msanDslSpecificMaxDelayDs {
          type int32 {
            range "-1..63";
          }
          units milliseconds;
          description
           "Maximum interleave delay for the downstream interleaved channel.
            -1 means that value from profile will be used (xdsl2ChConfProfMaxDelayDs).
            
            This object is created based on xdsl2ChConfProfMaxDelayDs (VDSL2-LINE MIB)";
          smiv2:max-access read-write;
          smiv2:oid 1.3.6.1.4.1.1332.1.1.5.3.19.3.1.4;
        }

        leaf msanDslSpecificMaxDelayUs {
          type int32 {
            range "-1..63";
          }
          units milliseconds;
          description
           "Maximum interleave delay for the upstream interleaved channel.
            -1 means that value from profile will be used (xdsl2ChConfProfMaxDelayUs).
            
            This object is created based on xdsl2ChConfProfMaxDelayUs (VDSL2-LINE MIB)";
          smiv2:max-access read-write;
          smiv2:oid 1.3.6.1.4.1.1332.1.1.5.3.19.3.1.5;
        }

        leaf msanDslSpecificMinProtectionDs {
          type int32 {
            range "-1..160";
          }
          units symbols;
          description
           "Downstream impulse noise protection.
            -1 means that value from profile will be used (xdsl2ChConfProfMinProtectionDs)
            
            This object is created based on xdsl2ChConfProfMinProtectionDs(VDSL2-LINE MIB)";
          smiv2:max-access read-write;
          smiv2:oid 1.3.6.1.4.1.1332.1.1.5.3.19.3.1.6;
        }

        leaf msanDslSpecificMinProtectionUs {
          type int32 {
            range "-1..160";
          }
          description
           "Upstream impulse noise protection.
            -1 means that value from profile will be used (xdsl2ChConfProfMinProtectionUs)
            
            This object is created based on xdsl2ChConfProfMinProtectionUs(VDSL2-LINE MIB)";
          smiv2:max-access read-write;
          smiv2:oid 1.3.6.1.4.1.1332.1.1.5.3.19.3.1.7;
        }

        leaf msanDslSpecificMaxSnrmDs {
          type uint32 {
            range "0..310";
          }
          units "0.1 dB";
          description
           "Downstream maximum Signal/Noise Margin.
            
            This object is created based on xdsl2LConfProfMaxSnrmDs (VDSL2-LINE MIB)";
          smiv2:max-access read-write;
          smiv2:oid 1.3.6.1.4.1.1332.1.1.5.3.19.3.1.8;
        }

        leaf msanDslSpecificMinSnrmDs {
          type uint32 {
            range "0..310";
          }
          units "0.1 dB";
          description
           "Downstream minimum Signal/Noise Margin.
            
            This object is created based on xdsl2LConfProfMinSnrmDs (VDSL2-LINE MIB)";
          smiv2:max-access read-write;
          smiv2:oid 1.3.6.1.4.1.1332.1.1.5.3.19.3.1.9;
        }

        leaf msanDslSpecificMaxSnrmUs {
          type uint32 {
            range "0..310";
          }
          units "0.1 dB";
          description
           "Upstream maximum Signal/Noise Margin.
            
            This object is created based on xdsl2LConfProfMaxSnrmUs (VDSL2-LINE MIB)";
          smiv2:max-access read-write;
          smiv2:oid 1.3.6.1.4.1.1332.1.1.5.3.19.3.1.10;
        }

        leaf msanDslSpecificMinSnrmUs {
          type uint32 {
            range "0..310";
          }
          units "0.1 dB";
          description
           "Upstream minimum Signal/Noise Margin.
            
            This object is created based on xdsl2LConfProfMinSnrmUs (VDSL2-LINE MIB)";
          smiv2:max-access read-write;
          smiv2:oid 1.3.6.1.4.1.1332.1.1.5.3.19.3.1.11;
        }

        leaf msanDslSpecificRaUsNrmDs {
          type uint32 {
            range "0..310";
          }
          units "0.1 dB";
          description
           "The Downstream Up-Shift Noise Margin (for dynamic rate adaptive
            mode).
            
            This object is created based on xdsl2LConfProfRaUsNrmDs (VDSL2-LINE MIB)";
          smiv2:max-access read-write;
          smiv2:oid 1.3.6.1.4.1.1332.1.1.5.3.19.3.1.12;
        }

        leaf msanDslSpecificRaUsNrmUs {
          type uint32 {
            range "0..310";
          }
          units "0.1 dB";
          description
           "The Upstream Up-Shift Noise Margin (for dynamic rate adaptive mode).
            
            This object is created based on xdsl2LConfProfRaUsNrmUs (VDSL2-LINE MIB)";
          smiv2:max-access read-write;
          smiv2:oid 1.3.6.1.4.1.1332.1.1.5.3.19.3.1.13;
        }

        leaf msanDslSpecificRaUsTimeDs {
          type uint32 {
            range "0..16383";
          }
          units seconds;
          description
           "The Downstream Up-Shift Time Interval (for rate dynamic adaptive
            mode).
            
            This object is created based on xdsl2LConfProfRaUsTimeDs (VDSL2-LINE MIB)";
          smiv2:max-access read-write;
          smiv2:oid 1.3.6.1.4.1.1332.1.1.5.3.19.3.1.14;
        }

        leaf msanDslSpecificRaUsTimeUs {
          type uint32 {
            range "0..16383";
          }
          units seconds;
          description
           "The Upstream Up-Shift Time Interval (for rate dynamic adaptive
            mode).
            
            This object is created based on xdsl2LConfProfRaUsTimeUs (VDSL2-LINE MIB)";
          smiv2:max-access read-write;
          smiv2:oid 1.3.6.1.4.1.1332.1.1.5.3.19.3.1.15;
        }

        leaf msanDslSpecificRaDsNrmDs {
          type uint32 {
            range "0..310";
          }
          units "0.1 dB";
          description
           "The Downstream Down-Shift Noise Margin (for dynamic rate adaptive
            mode).
            
            This object is created based on xdsl2LConfProfRaDsNrmDs (VDSL2-LINE MIB)";
          smiv2:max-access read-write;
          smiv2:oid 1.3.6.1.4.1.1332.1.1.5.3.19.3.1.16;
        }

        leaf msanDslSpecificRaDsNrmUs {
          type uint32 {
            range "0..310";
          }
          units "0.1 dB";
          description
           "The Upstream Down-Shift Noise Margin (for dynamic rate adaptive mode).
            
            This object is created based on xdsl2LConfProfRaDsNrmUs (VDSL2-LINE MIB)";
          smiv2:max-access read-write;
          smiv2:oid 1.3.6.1.4.1.1332.1.1.5.3.19.3.1.17;
        }

        leaf msanDslSpecificRaDsTimeDs {
          type uint32 {
            range "0..16383";
          }
          units seconds;
          description
           "The Downstream Down-Shift Time Interval (for rate dynamic adaptive
            mode).
            
            This object is created based on xdsl2LConfProfRaDsTimeDs (VDSL2-LINE MIB)";
          smiv2:max-access read-write;
          smiv2:oid 1.3.6.1.4.1.1332.1.1.5.3.19.3.1.18;
        }

        leaf msanDslSpecificRaDsTimeUs {
          type uint32 {
            range "0..16383";
          }
          units seconds;
          description
           "The Upstream Down-Shift Time Interval (for rate dynamic adaptive
            mode).
            
            This object is created based on xdsl2LConfProfRaDsTimeUs (VDSL2-LINE MIB)";
          smiv2:max-access read-write;
          smiv2:oid 1.3.6.1.4.1.1332.1.1.5.3.19.3.1.19;
        }

        leaf msanDslSpecificL0Time {
          type uint32 {
            range "0..255";
          }
          units seconds;
          description
           "The minimum time between an exit from the L2 state and the next entry
            into the L2 state.
            
            This object is created based on xdsl2LConfProfL0Time (VDSL2-LINE MIB)";
          smiv2:max-access read-write;
          smiv2:oid 1.3.6.1.4.1.1332.1.1.5.3.19.3.1.20;
        }

        leaf msanDslSpecificL2Time {
          type uint32 {
            range "0..255";
          }
          units seconds;
          description
           "The minimum time between an entry into the L2 state and the first
            power trim in the L2 state and between two consecutive power trims in
            the L2 State.
            
            This object is created based on xdsl2LConfProfL2Time (VDSL2-LINE MIB)";
          smiv2:max-access read-write;
          smiv2:oid 1.3.6.1.4.1.1332.1.1.5.3.19.3.1.21;
        }

        leaf msanDslSpecificL2Atpr {
          type uint32 {
            range "0..31";
          }
          units dB;
          description
           "The maximum aggregate transmit power reduction that can be performed
            at transition of L0 to L2 state or through a single power trim in the
            L2 state.
            
            This object is created based on xdsl2LConfProfL2Atpr (VDSL2-LINE MIB)";
          smiv2:max-access read-write;
          smiv2:oid 1.3.6.1.4.1.1332.1.1.5.3.19.3.1.22;
        }

        leaf msanDslSpecificL2Atprt {
          type uint32 {
            range "0..31";
          }
          units dB;
          description
           "The total maximum aggregate transmit power reduction that can be
            performed in an L2 state.
            
            This object is created based on xdsl2LConfProfL2Atprt (VDSL2-LINE MIB)";
          smiv2:max-access read-write;
          smiv2:oid 1.3.6.1.4.1.1332.1.1.5.3.19.3.1.23;
        }

        leaf msanDslSpecificScMaskDs {
          type binary {
            length "0..512";
          }
          description
           "Downstream Sub-carriers mask. A bitmap of 4096 bits that allows
            masking up to 4096 downstream sub-carriers.
            If bit is set to '1', the respective downstream sub-carrier is
            masked (not used), and if set to '0', the respective sub-carrier is
            unmasked.
            
            This object is created based on xdsl2LConfProfScMaskDs (VDSL2-LINE MIB)";
          smiv2:max-access read-write;
          smiv2:oid 1.3.6.1.4.1.1332.1.1.5.3.19.3.1.24;
        }

        leaf msanDslSpecificScMaskUs {
          type binary {
            length "0..512";
          }
          description
           "Upstream Sub-carriers mask. A bitmap of 4096 bits that allows
            masking up to 4096 downstream sub-carriers.
            If bit is set to '1', the respective downstream sub-carrier is
            masked (not used), and if set to '0', the respective sub-carrier is
            unmasked.
            
            This object is created based on xdsl2LConfProfScMaskUs (VDSL2-LINE MIB)";
          smiv2:max-access read-write;
          smiv2:oid 1.3.6.1.4.1.1332.1.1.5.3.19.3.1.25;
        }

        leaf msanDslSpecificRfiBands {
          type binary {
            length "0..64";
          }
          description
           "For VDLS, this configuration parameter defines the bands where the
            PSD shall be reduced. Each band shall be represented by a start and
            stop subcarrier indices with a subcarrier spacing of 4.3125 kHz. Up to
            16 bands may be specified. This parameter defines the RFI bands for
            both upstream and downstream          directions. Each RFI band is
            represented by 4 octets: 16 bit start sub-carrier index followed by a
            16 bit stop sub-carrier index.
            
            This object is created based on xdsl2LConfProfRfiBands (VDSL2-LINE MIB)";
          smiv2:max-access read-write;
          smiv2:oid 1.3.6.1.4.1.1332.1.1.5.3.19.3.1.26;
        }

        leaf msanDslSpecificMaxNomPsdDs {
          type int32 {
            range "-600..-300";
          }
          units "0.1 dBm/Hz";
          description
           "The maximum nominal transmit PSD in the downstream direction during
            initialization and Showtime. (0.1 dBm/Hz - physical values are -60 to
            -30 dBm/Hz).
            
            This object is created based on xdsl2LConfProfMaxNomPsdDs (VDSL2-LINE MIB)";
          smiv2:max-access read-write;
          smiv2:oid 1.3.6.1.4.1.1332.1.1.5.3.19.3.1.27;
        }

        leaf msanDslSpecificMaxNomPsdUs {
          type int32 {
            range "-600..-300";
          }
          units "0.1 dBm/Hz";
          description
           "The maximum nominal transmit PSD in the upstream direction during
            initialization and Showtime. (0.1 dBm/Hz - physical values are -60 to
            -30 dBm/Hz).
            
            This object is created based on xdsl2LConfProfMaxNomPsdUs (VDSL2-LINE MIB)";
          smiv2:max-access read-write;
          smiv2:oid 1.3.6.1.4.1.1332.1.1.5.3.19.3.1.28;
        }

        leaf msanDslSpecificMaxNomAtpDs {
          type uint32 {
            range "0..255";
          }
          units "0.1 dBm";
          description
           "The maximum nominal aggregate transmit power in the downstream
            direction during initialization and Showtime. (0.1 dBm - physical
            values are 0 to 25.5 dBm).
            
            This object is created based on xdsl2LConfProfMaxNomAtpDs (VDSL2-LINE MIB)";
          smiv2:max-access read-write;
          smiv2:oid 1.3.6.1.4.1.1332.1.1.5.3.19.3.1.29;
        }

        leaf msanDslSpecificMaxNomAtpUs {
          type uint32 {
            range "0..255";
          }
          units "0.1 dBm";
          description
           "The maximum nominal aggregate transmit power in the upstream
            direction during initialization and Showtime. (0.1 dBm - physical
            values are 0 to 25.5 dBm).
            
            This object is created based on xdsl2LConfProfMaxNomAtpUs (VDSL2-LINE MIB)";
          smiv2:max-access read-write;
          smiv2:oid 1.3.6.1.4.1.1332.1.1.5.3.19.3.1.30;
        }

        leaf msanDslSpecificMaxAggRxPwrUs {
          type int32 {
            range "-255..255";
          }
          units "0.1 dBm";
          description
           "The maximum upstream aggregate receive power over the relevant set of
            sub-carriers.. (0.1 dBm - physical values are -25.5 to 25.5 dBm).
            
            This object is created based on xdsl2LConfProfMaxAggRxPwrUs (VDSL2-LINE MIB)";
          smiv2:max-access read-write;
          smiv2:oid 1.3.6.1.4.1.1332.1.1.5.3.19.3.1.31;
        }

        leaf msanDslSpecificClassMask {
          type enumeration {
            enum b998M1xA {
              value 1;
            }
            enum b998M1xB {
              value 2;
            }
            enum b998M1xNUS0 {
              value 3;
            }
            enum b998M2xA {
              value 4;
            }
            enum b998M2xM {
              value 5;
            }
            enum b998M2xB {
              value 6;
            }
            enum b998M2xNUS0 {
              value 7;
            }
            enum b998E17M2xNUS0 {
              value 8;
            }
            enum b998E17M2xNUS0M {
              value 9;
            }
            enum b998ADE17M2xNUS0M {
              value 10;
            }
            enum b998ADE17M2xA {
              value 11;
            }
            enum b998ADE17M2xB {
              value 12;
            }
            enum b997M1cA7 {
              value 13;
            }
            enum b997M1xM8 {
              value 14;
            }
            enum b997M1xM {
              value 15;
            }
            enum b997M2xM8 {
              value 16;
            }
            enum b997M2xA {
              value 17;
            }
            enum b997M2xM {
              value 18;
            }
            enum bHPE17M1NUS0 {
              value 19;
            }
            enum bHPE30M1NUS0 {
              value 20;
            }
            enum b997E17M2xA {
              value 21;
            }
          }
          description
           "Predefined PSD mask.
            
            This object is created based on xdsl2LConfProfClassMask (VDSL2-LINE MIB)";
          smiv2:defval b998E17M2xNUS0;
          smiv2:max-access read-write;
          smiv2:oid 1.3.6.1.4.1.1332.1.1.5.3.19.3.1.32;
        }

        leaf msanDslSpecificDpboEsEL {
          type uint32 {
            range "0..511";
          }
          units "0.5 dB";
          description
           "Assumed electrical length of cables (E-side cables) connecting
            exchange based DSL services to a remote flexibility point (cabinet).
            The electrical length is defined as the loss (in dB) of an equivalent
            length of hypothetical cable at a reference frequency. 0 dB (coded as
            0) to 255.5 dB (coded as 511) in steps of 0.5 dB.
            
            This object is created based on xdsl2LConfProfDpboEsEL (VDSL2-LINE MIB)";
          smiv2:max-access read-write;
          smiv2:oid 1.3.6.1.4.1.1332.1.1.5.3.19.3.1.35;
        }

        leaf msanDslSpecificUpboKLF {
          type enumeration {
            enum auto {
              value 1;
            }
            enum override {
              value 2;
            }
            enum disableUpbo {
              value 3;
            }
          }
          description
           "Defines the upstream power backoff force mode.
            The three possible mode values are:
             auto(1),
             override(2),
             disableUpbo(3).
            
            This object is created based on xdsl2LConfProfUpboKLF (VDSL2-LINE MIB)";
          smiv2:max-access read-write;
          smiv2:oid 1.3.6.1.4.1.1332.1.1.5.3.19.3.1.36;
        }

        leaf msanDslSpecificUpboKL {
          type uint32 {
            range "0..1280";
          }
          units "0.1 dB";
          description
           "This configuration parameter defines the electrical length expressed
            in dB at 1MHz, configured by the CO-MIB. The value ranges from 0
            (coded as 0) to 128 dB (coded as 1280) in steps of 0.1 dB.
            
            This object is created based on xdsl2LConfProfUpboKL (VDSL2-LINE MIB)";
          smiv2:max-access read-write;
          smiv2:oid 1.3.6.1.4.1.1332.1.1.5.3.19.3.1.37;
        }

        leaf msanDslSpecificSelt {
          type enumeration {
            enum inhibit {
              value 1;
            }
            enum force {
              value 2;
            }
          }
          description
           "Defines whether the line should be forced into the SELT (Single-Ended Loop Testing)
            diagnostics mode by the near-end xTU of this line.
            Upon completion of the loop diagnostic mode procedures, the Access Node shall set
            this object to 'inhibit'.
            The results of the SELT procedure are stored in the table msanDslSeltStatusTable.
            The status of the loop diagnostic procedure is indicated by msanDslSpecificSeltStatus.";
          smiv2:defval inhibit;
          smiv2:max-access read-write;
          smiv2:oid 1.3.6.1.4.1.1332.1.1.5.3.19.3.1.39;
        }

        leaf msanDslSpecificSeltStatus {
          type enumeration {
            enum none {
              value 1;
            }
            enum success {
              value 2;
            }
            enum inProgress {
              value 3;
            }
            enum unsupported {
              value 4;
            }
            enum cannotRun {
              value 5;
            }
            enum aborted {
              value 6;
            }
            enum failed {
              value 7;
            }
            enum illegalMode {
              value 8;
            }
            enum adminUp {
              value 9;
            }
            enum tableFull {
              value 10;
            }
            enum noResources {
              value 11;
            }
            enum undefinedError {
              value 12;
            }
          }
          description
           "SELT (Single-Ended Loop Testing) status of dsl line. ";
          smiv2:max-access read-only;
          smiv2:oid 1.3.6.1.4.1.1332.1.1.5.3.19.3.1.40;
        }

        leaf msanDslSpecificPhyRDs {
          type enumeration {
            enum disabled {
              value 1;
            }
            enum enabled {
              value 2;
            }
            enum auto {
              value 3;
            }
          }
          description
           "Physical Layer Retransmission configuration in the downstream direction. ";
          smiv2:defval auto;
          smiv2:max-access read-write;
          smiv2:oid 1.3.6.1.4.1.1332.1.1.5.3.19.3.1.41;
        }

        leaf msanDslSpecificPhyRUs {
          type enumeration {
            enum disabled {
              value 1;
            }
            enum enabled {
              value 2;
            }
            enum auto {
              value 3;
            }
          }
          description
           "Physical Layer Retransmission configuration in the upstream direction. ";
          smiv2:defval auto;
          smiv2:max-access read-write;
          smiv2:oid 1.3.6.1.4.1.1332.1.1.5.3.19.3.1.42;
        }

        leaf msanDslSpecificUpboUs1a {
          type int32 {
            range "4000..8095";
          }
          units "0.01 dBm/Hz";
          description
           "ITU-T G.997.1, paragraph #7.3.1.2.14 (UPBOPSD-pb)
            
            Parameter defines the 'a' reference parameter of the UPBO reference PSD
            used to compute the upstream power back-off for the upstream band.
            A UPBO PSD defined for each band shall consist of two parameters [a, b].
            
            Parameter 'a' (xdsl2LConfProfUpboPsdA) ranges from 40 dBm/Hz (coded as
            4000) to 80.95 dBm/Hz (coded as 8095) in steps of 0.01 dBm/Hz; and
            parameter 'b' (xdsl2LConfProfUpboPsdB) ranges from 0 dBm/Hz (coded as 0)
            to 40.95 dBm/Hz (coded as 4095) in steps of 0.01 dBm/Hz.
            
            The UPBO reference PSD at the frequency 'f' expressed in MHz shall be
            equal to '-a-b(SQRT(f))'. Setting xdsl2LConfProfUpboPsdA to 4000 and
            xdsl2LConfProfUpboPsdB to 0 is  a special configuration to disable UPBO in
            the respective  upstream band.";
          smiv2:defval 4000;
          smiv2:max-access read-write;
          smiv2:oid 1.3.6.1.4.1.1332.1.1.5.3.19.3.1.43;
        }

        leaf msanDslSpecificUpboUs1b {
          type int32 {
            range "0..4095";
          }
          units "0.01 dBm/Hz";
          description
           "ITU-T G.997.1, paragraph #7.3.1.2.14 (UPBOPSD-pb)
            
            Parameter defines the 'b' reference parameter of the UPBO
            reference PSD used to compute the upstream power back-off for the
            upstream band. Parameter 'b' (xdsl2LConfProfUpboPsdB) ranges from
            0 dBm/Hz (coded as 0) to 40.95 dBm/Hz (coded as 4095) in steps of 0.01 dBm/Hz. ";
          smiv2:defval 0;
          smiv2:max-access read-write;
          smiv2:oid 1.3.6.1.4.1.1332.1.1.5.3.19.3.1.44;
        }

        leaf msanDslSpecificUpboUs2a {
          type int32 {
            range "4000..8095";
          }
          units "0.01 dBm/Hz";
          description
           "ITU-T G.997.1, paragraph #7.3.1.2.14 (UPBOPSD-pb)
            
            Parameter defines the 'a' reference parameter of the UPBO reference PSD
            used to compute the upstream power back-off for the upstream band.
            A UPBO PSD defined for each band shall consist of two parameters [a, b].
            
            Parameter 'a' (xdsl2LConfProfUpboPsdA) ranges from 40 dBm/Hz (coded as
            4000) to 80.95 dBm/Hz (coded as 8095) in steps of 0.01 dBm/Hz; and
            parameter 'b' (xdsl2LConfProfUpboPsdB) ranges from 0 dBm/Hz (coded as 0)
            to 40.95 dBm/Hz (coded as 4095) in steps of 0.01 dBm/Hz.
            
            The UPBO reference PSD at the frequency 'f' expressed in MHz shall be
            equal to '-a-b(SQRT(f))'. Setting xdsl2LConfProfUpboPsdA to 4000 and
            xdsl2LConfProfUpboPsdB to 0 is  a special configuration to disable UPBO in
            the respective  upstream band.";
          smiv2:defval 4000;
          smiv2:max-access read-write;
          smiv2:oid 1.3.6.1.4.1.1332.1.1.5.3.19.3.1.45;
        }

        leaf msanDslSpecificUpboUs2b {
          type int32 {
            range "0..4095";
          }
          units "0.01 dBm/Hz";
          description
           "ITU-T G.997.1, paragraph #7.3.1.2.14 (UPBOPSD-pb)
            
            Parameter defines the 'b' reference parameter of the UPBO
            reference PSD used to compute the upstream power back-off for the
            upstream band. Parameter 'b' (xdsl2LConfProfUpboPsdB) ranges from
            0 dBm/Hz (coded as 0) to 40.95 dBm/Hz (coded as 4095) in steps of 0.01 dBm/Hz. ";
          smiv2:defval 0;
          smiv2:max-access read-write;
          smiv2:oid 1.3.6.1.4.1.1332.1.1.5.3.19.3.1.46;
        }

        leaf msanDslSpecificUpboUs3a {
          type int32 {
            range "4000..8095";
          }
          units "0.01 dBm/Hz";
          description
           "ITU-T G.997.1, paragraph #7.3.1.2.14 (UPBOPSD-pb)
            
            Parameter defines the 'a' reference parameter of the UPBO reference PSD
            used to compute the upstream power back-off for the upstream band.
            A UPBO PSD defined for each band shall consist of two parameters [a, b].
            
            Parameter 'a' (xdsl2LConfProfUpboPsdA) ranges from 40 dBm/Hz (coded as
            4000) to 80.95 dBm/Hz (coded as 8095) in steps of 0.01 dBm/Hz; and
            parameter 'b' (xdsl2LConfProfUpboPsdB) ranges from 0 dBm/Hz (coded as 0)
            to 40.95 dBm/Hz (coded as 4095) in steps of 0.01 dBm/Hz.
            
            The UPBO reference PSD at the frequency 'f' expressed in MHz shall be
            equal to '-a-b(SQRT(f))'. Setting xdsl2LConfProfUpboPsdA to 4000 and
            xdsl2LConfProfUpboPsdB to 0 is  a special configuration to disable UPBO in
            the respective  upstream band.";
          smiv2:defval 4000;
          smiv2:max-access read-write;
          smiv2:oid 1.3.6.1.4.1.1332.1.1.5.3.19.3.1.47;
        }

        leaf msanDslSpecificUpboUs3b {
          type int32 {
            range "0..4095";
          }
          units "0.01 dBm/Hz";
          description
           "ITU-T G.997.1, paragraph #7.3.1.2.14 (UPBOPSD-pb)
            
            Parameter defines the 'b' reference parameter of the UPBO
            reference PSD used to compute the upstream power back-off for the
            upstream band. Parameter 'b' (xdsl2LConfProfUpboPsdB) ranges from
            0 dBm/Hz (coded as 0) to 40.95 dBm/Hz (coded as 4095) in steps of 0.01 dBm/Hz. ";
          smiv2:defval 0;
          smiv2:max-access read-write;
          smiv2:oid 1.3.6.1.4.1.1332.1.1.5.3.19.3.1.48;
        }

        leaf msanDslSpecificUpboUs4a {
          type int32 {
            range "4000..8095";
          }
          units "0.01 dBm/Hz";
          description
           "ITU-T G.997.1, paragraph #7.3.1.2.14 (UPBOPSD-pb)
            
            Parameter defines the 'a' reference parameter of the UPBO reference PSD
            used to compute the upstream power back-off for the upstream band.
            A UPBO PSD defined for each band shall consist of two parameters [a, b].
            
            Parameter 'a' (xdsl2LConfProfUpboPsdA) ranges from 40 dBm/Hz (coded as
            4000) to 80.95 dBm/Hz (coded as 8095) in steps of 0.01 dBm/Hz; and
            parameter 'b' (xdsl2LConfProfUpboPsdB) ranges from 0 dBm/Hz (coded as 0)
            to 40.95 dBm/Hz (coded as 4095) in steps of 0.01 dBm/Hz.
            
            The UPBO reference PSD at the frequency 'f' expressed in MHz shall be
            equal to '-a-b(SQRT(f))'. Setting xdsl2LConfProfUpboPsdA to 4000 and
            xdsl2LConfProfUpboPsdB to 0 is  a special configuration to disable UPBO in
            the respective  upstream band.";
          smiv2:defval 4000;
          smiv2:max-access read-write;
          smiv2:oid 1.3.6.1.4.1.1332.1.1.5.3.19.3.1.49;
        }

        leaf msanDslSpecificUpboUs4b {
          type int32 {
            range "0..4095";
          }
          units "0.01 dBm/Hz";
          description
           "ITU-T G.997.1, paragraph #7.3.1.2.14 (UPBOPSD-pb)
            
            Parameter defines the 'b' reference parameter of the UPBO
            reference PSD used to compute the upstream power back-off for the
            upstream band. Parameter 'b' (xdsl2LConfProfUpboPsdB) ranges from
            0 dBm/Hz (coded as 0) to 40.95 dBm/Hz (coded as 4095) in steps of 0.01 dBm/Hz. ";
          smiv2:defval 0;
          smiv2:max-access read-write;
          smiv2:oid 1.3.6.1.4.1.1332.1.1.5.3.19.3.1.50;
        }

        leaf msanDslSpecificDpboEPsdMask {
          type binary;
          description
           "DPbo EPsd mask name.
            It should be of the downstream PSD mask as defined by msanDslPsdMaskDsName.";
          smiv2:defval "";
          smiv2:max-access read-write;
          smiv2:oid 1.3.6.1.4.1.1332.1.1.5.3.19.3.1.51;
        }

        leaf msanDslSpecificDpboEsCmA {
          type uint32 {
            range "0..640";
          }
          units 2^-8;
          description
           "ITU-T G.997.1, paragraph #7.3.1.2.13 (DPBOESCMA)
            
            The E-side Cable Model parameter A (DPBOESCMA) of the cable  model
            (DPBOESCM) for cables connecting exchange-based DSL services to a remote
            flexibility point (cabinet), that hosts the xTU-C that is subject to spectrally shaped
            downstream power back- off (DPBO) depending on this value.
            Possible values shall be coded as unsigned integers representing a scalar value
            from -1 (coded as 0) to 1.5 (coded as 640) in steps of 2-8 All values in the range are
            valid.";
          reference
           "ITU-T G.997.1, paragraph #7.3.1.2.13 (DPBOESCMA)";
          smiv2:defval 0;
          smiv2:max-access read-write;
          smiv2:oid 1.3.6.1.4.1.1332.1.1.5.3.19.3.1.52;
        }

        leaf msanDslSpecificDpboEsCmB {
          type uint32 {
            range "0..640";
          }
          units 2^-8;
          description
           "ITU-T G.997.1, paragraph #7.3.1.2.13 (DPBOESCMB)
            
            The E-side Cable Model parameter B (DPBOESCMB) of the cable  model
            (DPBOESCM) for cables connecting exchange-based DSL services to a remote
            flexibility point (cabinet), that hosts the xTU-C that is subject to spectrally shaped
            downstream power back- off (DPBO) depending on this value.
            Possible values shall be coded as unsigned integers representing a scalar value
            from -1 (coded as 0) to 1.5 (coded as 640) in steps of 2-8 All values in the range are
            valid.";
          reference
           "ITU-T G.997.1, paragraph #7.3.1.2.13 (DPBOESCMB)";
          smiv2:defval 0;
          smiv2:max-access read-write;
          smiv2:oid 1.3.6.1.4.1.1332.1.1.5.3.19.3.1.53;
        }

        leaf msanDslSpecificDpboEsCmC {
          type uint32 {
            range "0..640";
          }
          units 2^-8;
          description
           "ITU-T G.997.1, paragraph #7.3.1.2.13 (DPBOESCMC)
            
            The E-side Cable Model parameter C (DPBOESCMC) of the cable  model
            (DPBOESCM) for cables connecting exchange-based DSL services to a remote
            flexibility point (cabinet), that hosts the xTU-C that is subject to spectrally shaped
            downstream power back- off (DPBO) depending on this value.
            Possible values shall be coded as unsigned integers representing a scalar value
            from -1 (coded as 0) to 1.5 (coded as 640) in steps of 2-8 All values in the range are
            valid.";
          reference
           "ITU-T G.997.1, paragraph #7.3.1.2.13 (DPBOESCMC)";
          smiv2:defval 0;
          smiv2:max-access read-write;
          smiv2:oid 1.3.6.1.4.1.1332.1.1.5.3.19.3.1.54;
        }

        leaf msanDslSpecificDpboMus {
          type uint32 {
            range "0..255";
          }
          units "0.5 dBm/Hz";
          description
           "ITU-T G.997.1, paragraph #7.3.1.2.13 (DPBOMUS)
            
            Assumed Minimum Usable receive PSD mask (in dBm/Hz) for exchange-based
            services.
            It shall be coded as an unsigned integer representing a PSD mask level from
            0 dBm/Hz  (coded as 0) to -127.5 dBm/Hz (coded as 255) in steps of 0.5  dBm/Hz.
            All values in the range are valid.";
          reference
           "ITU-T G.997.1, paragraph #7.3.1.2.13 (DPBOMUS)";
          smiv2:defval 0;
          smiv2:max-access read-write;
          smiv2:oid 1.3.6.1.4.1.1332.1.1.5.3.19.3.1.55;
        }

        leaf msanDslSpecificDpboFMin {
          type uint32 {
            range "0..2048";
          }
          units "4.3125 kHz";
          description
           "ITU-T G.997.1, paragraph #7.3.1.2.13 (DPBOFMIN)
            
            Minimum frequency from which the DPBO shall be applied.
            It ranges from 0 kHz (coded as 0) to 8832 kHz (coded as 2048) in steps of 4.3125 kHz.";
          reference
           "ITU-T G.997.1, paragraph #7.3.1.2.13 (DPBOFMIN)";
          smiv2:defval 32;
          smiv2:max-access read-write;
          smiv2:oid 1.3.6.1.4.1.1332.1.1.5.3.19.3.1.56;
        }

        leaf msanDslSpecificDpboFMax {
          type uint32 {
            range "32..6956";
          }
          units "4.3125 kHz";
          description
           "ITU-T G.997.1, paragraph #7.3.1.2.13 (DPBOFMAX)
            
            Maximum frequency at which DPBO may be applied.
            It ranges from 138 kHz (coded as 32) to 29997.75 kHz (coded as 6956) in steps of 4.3125 kHz.";
          reference
           "ITU-T G.997.1, paragraph #7.3.1.2.13 (DPBOFMAX)";
          smiv2:defval 512;
          smiv2:max-access read-write;
          smiv2:oid 1.3.6.1.4.1.1332.1.1.5.3.19.3.1.57;
        }

        leaf msanDslSpecificVectorModeEnable {
          type bits {
            bit vdsl2Only {
              position 0;
            }
            bit vectoringFriendlyDs {
              position 1;
            }
            bit vectoringFriendlyDsUs {
              position 2;
            }
            bit vectoringFully {
              position 3;
            }
          }
          description
           "Type of vectoring initialization to be allowed by the VTU-O on the line.
            ITU-T G.997.1, paragraph #7.3.1.13.9  (VECTORMODE_ENABLE).
            
            This configuration parameter defines the vectoring initialization type to be
            allowed by the VTU-O on the line. It is coded in a bit-map representation (0
            if not allowed, 1 if allowed).";
          smiv2:defval "{}";
          smiv2:max-access read-write;
          smiv2:oid 1.3.6.1.4.1.1332.1.1.5.3.19.3.1.58;
        }

        leaf msanDslSpecificVectorModeState {
          type bits {
            bit vdsl2Only {
              position 0;
            }
            bit vectoringFriendlyDs {
              position 1;
            }
            bit vectoringFriendlyDsUs {
              position 2;
            }
            bit vectoringFully {
              position 3;
            }
          }
          description
           "Current vectoring initialization type on the line.
            
            Line can operate only in common vdsl2 (non/vectoring)
            or in one of vectoring modes therefore only one bit may be set to 1. ";
          smiv2:max-access read-only;
          smiv2:oid 1.3.6.1.4.1.1332.1.1.5.3.19.3.1.59;
        }
      }
    }

    container msanDslPsdMaskDsTable {
      description
       "Management of Downstream PSD Mask (G997.1 #7.3.1.2.9 )";
      smiv2:oid 1.3.6.1.4.1.1332.1.1.5.3.19.4;

      list msanDslPsdMaskDsEntry {
        key msanDslPsdMaskDsName;
        description
         "Description.";
        smiv2:oid 1.3.6.1.4.1.1332.1.1.5.3.19.4.1;

        leaf msanDslPsdMaskDsName {
          type binary {
            length "1..32";
          }
          description
           "Downstream custom PSD mask name.";
          smiv2:max-access not-accessible;
          smiv2:oid 1.3.6.1.4.1.1332.1.1.5.3.19.4.1.1;
        }

        leaf msanDslPsdMaskDsType {
          type enumeration {
            enum default {
              value 1;
            }
            enum configured {
              value 2;
            }
          }
          description
           "Downstream custom PSD mask type.
            
            Possible values:
            default(1) - Default mask prepared by vendor, user is not allowed to delete or change it
            configured(2) - Mask created by user";
          smiv2:defval 144685360;
          smiv2:max-access read-only;
          smiv2:oid 1.3.6.1.4.1.1332.1.1.5.3.19.4.1.2;
        }

        leaf msanDslPsdMaskDsShape {
          type iskratel-msan:Xdsl2PsdMaskDs;
          description
           "The downstream PSD mask applicable at the U-C2 reference point.
            
            This parameter is used only for G.992.5 and it may impose PSD
            restrictions (breakpoints) in addition to the Limit PSD mask
            defined in G.992.5.
            This is a string of 32 pairs of values in the following
            structure:
            Octets 0-1 - Index of the first subcarrier used in the context of
             	             a first breakpoint.
            Octet 2    - The PSD reduction for the subcarrier indicated in
             	             octets 0 and 1.
            Octets 3-5 - Same, for a second breakpoint.
            Octets 6-8 - Same, for a third breakpoint.
            This architecture continues until octets 94-95, which are
            associated with a 32nd breakpoint.
            Each subcarrier index is an unsigned number in the range 0 and
            NSCds-1.  Each PSD reduction value is in the range 0 (0 dBm/Hz) to
            255 (-127.5 dBm/Hz) with steps of 0.5 dBm/Hz.  Valid values are in
            the range 0 to 190 (0 to -95 dBm/Hz).
            When the number of breakpoints is less than 32, all remaining
            octets are set to the value '0'.  Note that the content of this
            object should be correlated with the subcarrier mask and with
            the RFI setup.";
          smiv2:defval "'00'H";
          smiv2:max-access read-write;
          smiv2:oid 1.3.6.1.4.1.1332.1.1.5.3.19.4.1.3;
        }

        leaf msanDslPsdMaskDsRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.19.4.1.4;
        }
      }
    }

    container msanDslPsdMaskUsTable {
      description
       "Management of Upstream PSD Mask (G997.1 #7.3.1.2.9 )";
      smiv2:oid 1.3.6.1.4.1.1332.1.1.5.3.19.5;

      list msanDslPsdMaskUsEntry {
        key msanDslPsdMaskUsName;
        description
         "Description.";
        smiv2:oid 1.3.6.1.4.1.1332.1.1.5.3.19.5.1;

        leaf msanDslPsdMaskUsName {
          type binary {
            length "1..32";
          }
          description
           "Upstream custom PSD mask name.";
          smiv2:max-access not-accessible;
          smiv2:oid 1.3.6.1.4.1.1332.1.1.5.3.19.5.1.1;
        }

        leaf msanDslPsdMaskUsType {
          type enumeration {
            enum default {
              value 1;
            }
            enum configured {
              value 2;
            }
          }
          description
           "Downstream custom PSD mask type.
            
            Possible values:
            default(1) - Default mask prepared by vendor, user is not allowed to delete or change it
            configured(2) - Mask created by user";
          smiv2:defval 144689264;
          smiv2:max-access read-only;
          smiv2:oid 1.3.6.1.4.1.1332.1.1.5.3.19.5.1.2;
        }

        leaf msanDslPsdMaskUsShape {
          type iskratel-msan:Xdsl2PsdMaskUs;
          description
           "The upstream PSD mask applicable at the U-R2 reference point.
            
            This parameter is used only for G.992.5, and it may impose PSD
            restrictions (breakpoints) in addition to the Limit PSD mask
            defined in G.992.5.
            This is a string of 16 pairs of values in the following
            structure:
            Octets 0-1 - Index of the first subcarrier used in the context of
             	             a first breakpoint.
            Octet 2    - The PSD reduction for the subcarrier indicated in
             	             octets 0 and 1.
            Octets 3-5 - Same, for a second breakpoint.
            Octets 6-8 - Same, for a third breakpoint.
            This architecture continues until octets 9-47, which are
            associated with a 16th breakpoint.
            Each subcarrier index is an unsigned number in the range 0 and
            NSCus-1.  Each PSD reduction value is in the range 0 (0 dBm/Hz) to
            255 (-127.5 dBm/Hz) with steps of 0.5 dBm/Hz.  Valid values are in
            the range 0 to 190 (0 to -95 dBm/Hz).
            When the number of breakpoints is less than 16, all remaining
            octets are set to the value '0'.  Note that the content of this
            object should be correlated with the subcarrier mask and with
            the RFI setup.";
          smiv2:defval "'00'H";
          smiv2:max-access read-write;
          smiv2:oid 1.3.6.1.4.1.1332.1.1.5.3.19.5.1.3;
        }

        leaf msanDslPsdMaskUsRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.19.5.1.4;
        }
      }
    }

    container msanDslSeltStatusTable {
      description
       "Description.";
      smiv2:oid 1.3.6.1.4.1.1332.1.1.5.3.19.6;

      list msanDslSeltStatusEntry {
        key ifIndex;
        description
         "Description.";
        smiv2:oid 1.3.6.1.4.1.1332.1.1.5.3.19.6.1;

        leaf ifIndex {
          type leafref {
            path "/if-mib:interfaces/if-mib:ifEntry/if-mib:ifIndex";
          }
        }

        leaf msanDslSeltStatusNoiseType {
          type binary {
            length "0..30";
          }
          description
           "Noise type.";
          smiv2:max-access read-only;
          smiv2:oid 1.3.6.1.4.1.1332.1.1.5.3.19.6.1.1;
        }

        leaf msanDslSeltStatusNoiseMrgDs {
          type int32;
          units "0.1 dB";
          description
           "Noise margin in DS direction. [0.1 dB]";
          smiv2:max-access read-only;
          smiv2:oid 1.3.6.1.4.1.1332.1.1.5.3.19.6.1.2;
        }

        leaf msanDslSeltStatusNoiseMrgUs {
          type int32;
          units "0.1 dB";
          description
           "Noise margin in US direction. [0.1 dB]";
          smiv2:max-access read-only;
          smiv2:oid 1.3.6.1.4.1.1332.1.1.5.3.19.6.1.3;
        }

        leaf msanDslSeltStatusNumTonesDs {
          type int32;
          description
           "Number of tones used for SELT in DS direction. ";
          smiv2:max-access read-only;
          smiv2:oid 1.3.6.1.4.1.1332.1.1.5.3.19.6.1.4;
        }

        leaf msanDslSeltStatusNumTonesUs {
          type int32;
          description
           "Number of tones used for SELT in US direction. ";
          smiv2:max-access read-only;
          smiv2:oid 1.3.6.1.4.1.1332.1.1.5.3.19.6.1.5;
        }

        leaf msanDslSeltStatusMaxRateDs {
          type int32;
          units kbps;
          description
           "Maximum Downstream capacity [kbps]";
          smiv2:max-access read-only;
          smiv2:oid 1.3.6.1.4.1.1332.1.1.5.3.19.6.1.6;
        }

        leaf msanDslSeltStatusMaxRateUs {
          type int32;
          units kbps;
          description
           "Maximum Upstream capacity [kbps]";
          smiv2:max-access read-only;
          smiv2:oid 1.3.6.1.4.1.1332.1.1.5.3.19.6.1.7;
        }

        leaf msanDslSeltStatusCableType {
          type binary {
            length "0..20";
          }
          description
           "DSL line loop type.";
          smiv2:max-access read-only;
          smiv2:oid 1.3.6.1.4.1.1332.1.1.5.3.19.6.1.8;
        }

        leaf msanDslSeltStatusCableLenght {
          type int32;
          units m;
          description
           "DSL line loop lenght. [m]";
          smiv2:max-access read-only;
          smiv2:oid 1.3.6.1.4.1.1332.1.1.5.3.19.6.1.9;
        }

        leaf msanDslSeltStatusFitError {
          type int32;
          units %;
          description
           "DSL Line lenght fit error. [%]";
          smiv2:max-access read-only;
          smiv2:oid 1.3.6.1.4.1.1332.1.1.5.3.19.6.1.10;
        }

        leaf msanDslSeltStatusLoopTermination {
          type enumeration {
            enum unknown {
              value 1;
            }
            enum open {
              value 2;
            }
            enum short {
              value 3;
            }
          }
          description
           "Type of DSL line termination. ";
          smiv2:max-access read-only;
          smiv2:oid 1.3.6.1.4.1.1332.1.1.5.3.19.6.1.11;
        }
      }
    }

    container msanDslAtmPvcTable {
      description
       "ATM PVC configuration of the ADSL port";
      smiv2:oid 1.3.6.1.4.1.1332.1.1.5.3.19.7;

      list msanDslAtmPvcEntry {
        key ifIndex;
        description
         "Description.";
        smiv2:oid 1.3.6.1.4.1.1332.1.1.5.3.19.7.1;

        leaf ifIndex {
          type leafref {
            path "/if-mib:interfaces/if-mib:ifEntry/if-mib:ifIndex";
          }
        }

        leaf msanDslAtmPvcVpi {
          type int32 {
            range "-1..255";
          }
          description
           "ATM Virtual path identifier of the ADSL PVC interface.
            Value -1 indicates that parameter has not been defined.";
          smiv2:defval -1;
          smiv2:max-access read-write;
          smiv2:oid 1.3.6.1.4.1.1332.1.1.5.3.19.7.1.2;
        }

        leaf msanDslAtmPvcVci {
          type int32 {
            range "31..65535";
          }
          description
           "ATM Virtual channel identifier of the ADSL PVC interface.
            Value 31 indicates that parameter has not been defined.";
          smiv2:defval 31;
          smiv2:max-access read-write;
          smiv2:oid 1.3.6.1.4.1.1332.1.1.5.3.19.7.1.3;
        }
      }
    }

    container msanPortMirroringTable {
      description
       "Description.";
      smiv2:oid 1.3.6.1.4.1.1332.1.1.5.3.20.2;

      list msanPortMirroringEntry {
        key msanPortMirroringSessionId;
        description
         "Description.";
        smiv2:oid 1.3.6.1.4.1.1332.1.1.5.3.20.2.1;

        leaf msanPortMirroringSessionId {
          type int32;
          description
           "The Session number of this mirroring entry.";
          smiv2:max-access not-accessible;
          smiv2:oid 1.3.6.1.4.1.1332.1.1.5.3.20.2.1.1;
        }

        leaf msanPortMirroringAdminState {
          type enumeration {
            enum disable {
              value 0;
            }
            enum enable {
              value 1;
            }
          }
          description
           "The status of this port mirroring session. ";
          smiv2:max-access read-write;
          smiv2:oid 1.3.6.1.4.1.1332.1.1.5.3.20.2.1.2;
        }

        leaf msanPortMirroringDestPort {
          type int32;
          description
           "The port which traffic from the mirrored ports will be sent to.
            Port value is ifIndex from ifTable. Value 0 means, port is not defined.";
          smiv2:max-access read-write;
          smiv2:oid 1.3.6.1.4.1.1332.1.1.5.3.20.2.1.3;
        }
      }
    }

    container msanPortMirroringMemberTable {
      description
       "Description.";
      smiv2:oid 1.3.6.1.4.1.1332.1.1.5.3.20.3;

      list msanPortMirroringMemberEntry {
        key "msanPortMirroringSessionId msanPortMirroringMemberSrcPort";
        description
         "Description.";
        smiv2:oid 1.3.6.1.4.1.1332.1.1.5.3.20.3.1;

        leaf msanPortMirroringSessionId {
          type leafref {
            path "/iskratel-msan:ISKRATEL-MSAN-MIB/iskratel-msan:msanPortMirroringTable/iskratel-msan:msanPortMirroringEntry/iskratel-msan:msanPortMirroringSessionId";
          }
        }

        leaf msanPortMirroringMemberSrcPort {
          type int32;
          description
           "The port from which traffic will be sent to the destination port. ";
          smiv2:max-access not-accessible;
          smiv2:oid 1.3.6.1.4.1.1332.1.1.5.3.20.3.1.1;
        }

        leaf msanPortMirroringMemberDirection {
          type enumeration {
            enum tx {
              value 1;
            }
            enum rx {
              value 2;
            }
            enum txAndRx {
              value 3;
            }
          }
          description
           "The direction of the data to be mirrored on this source port. ";
          smiv2:max-access read-write;
          smiv2:oid 1.3.6.1.4.1.1332.1.1.5.3.20.3.1.2;
        }

        leaf msanPortMirroringMemberRowStatus {
          type snmpv2-tc:RowStatus;
          description
           "The row status object controls the creation/deletion of rows in this table.
            For row creation use createAndWait(5) [createAndGo(4) is not supported].";
          smiv2:max-access read-write;
          smiv2:oid 1.3.6.1.4.1.1332.1.1.5.3.20.3.1.3;
        }
      }
    }

    container msanMacTableCAMTable {
      description
       "Description.";
      smiv2:oid 1.3.6.1.4.1.1332.1.1.5.3.22.2;

      list msanMacTableCAMEntry {
        key msanMacTableCAMIndex;
        description
         "Description.";
        smiv2:oid 1.3.6.1.4.1.1332.1.1.5.3.22.2.1;

        leaf msanMacTableCAMIndex {
          type int32;
          description
           "Id of the CAM entry.";
          smiv2:max-access not-accessible;
          smiv2:oid 1.3.6.1.4.1.1332.1.1.5.3.22.2.1.1;
        }

        leaf msanMacTableMacAddress {
          type yang:mac-address;
          description
           "MAC address of the CAM entry. ";
          smiv2:max-access read-only;
          smiv2:oid 1.3.6.1.4.1.1332.1.1.5.3.22.2.1.2;
        }

        leaf msanMacTablePort {
          type int32;
          description
           "The port on which MAC address was learned or defined. ";
          smiv2:max-access read-only;
          smiv2:oid 1.3.6.1.4.1.1332.1.1.5.3.22.2.1.3;
        }

        leaf msanMacTableVLAN {
          type int32;
          description
           "VLAN id of the learned or defined MAC address. ";
          smiv2:max-access read-only;
          smiv2:oid 1.3.6.1.4.1.1332.1.1.5.3.22.2.1.4;
        }

        leaf msanMacTableType {
          type enumeration {
            enum learned {
              value 1;
            }
            enum managment {
              value 2;
            }
            enum static {
              value 3;
            }
          }
          description
           "Type of the MAC address.  ";
          smiv2:max-access read-only;
          smiv2:oid 1.3.6.1.4.1.1332.1.1.5.3.22.2.1.5;
        }
      }
    }

    container msanStpBpduFilterTable {
      description
       "Description.";
      smiv2:oid 1.3.6.1.4.1.1332.1.1.5.3.24.2;

      list msanStpBpduFilterEntry {
        key ifIndex;
        description
         "Description.";
        smiv2:oid 1.3.6.1.4.1.1332.1.1.5.3.24.2.1;

        leaf ifIndex {
          type leafref {
            path "/if-mib:interfaces/if-mib:ifEntry/if-mib:ifIndex";
          }
        }

        leaf msanStpBpduFilter {
          type enumeration {
            enum disable {
              value 0;
            }
            enum enable {
              value 1;
            }
          }
          description
           "Defines how BPDU packets are handled in case stp_port_state is disabled.
            
            0   disable - If stp_port_state is disabled on interface, forward all
            BPDUs unchanged to all other interfaces that also have stp_port_state
            disabled.
            1   enable - If stp_port_state is disabled on interface, drop all
            BPDUs received on the interface. ";
          smiv2:max-access read-write;
          smiv2:oid 1.3.6.1.4.1.1332.1.1.5.3.24.2.1.1;
        }
      }
    }

    container msanStpMstTable {
      description
       "Description.";
      reference
       "agentStpMstTable - 1.3.6.1.4.1.6132.1.1.1.2.15.10";
      smiv2:oid 1.3.6.1.4.1.1332.1.1.5.3.24.4;

      list msanStpMstEntry {
        key msanStpMstId;
        description
         "Description.";
        smiv2:oid 1.3.6.1.4.1.1332.1.1.5.3.24.4.1;

        leaf msanStpMstId {
          type uint32;
          description
           "The MSTP instance ID. Instance 0 is not shown. ";
          smiv2:max-access not-accessible;
          smiv2:oid 1.3.6.1.4.1.1332.1.1.5.3.24.4.1.1;
        }

        leaf msanStpMstBridgePriority {
          type uint32 {
            range "0..61440";
          }
          description
           "The MSTP bridge priority in a specific instance. The priority is
            in the increments of 4096. The recommended default value is 32768.";
          smiv2:max-access read-write;
          smiv2:oid 1.3.6.1.4.1.1332.1.1.5.3.24.4.1.2;
        }

        leaf msanStpMstRowStatus {
          type snmpv2-tc:RowStatus;
          description
           "The MSTP instance status. Instance 0 is not shown.
            
            Supported values:
            active(1) - valid instance.
            createAndGo(4) - used to create a new instance.
            destroy(6)     - removes an instance.";
          smiv2:max-access read-write;
          smiv2:oid 1.3.6.1.4.1.1332.1.1.5.3.24.4.1.3;
        }
      }
    }

    container msanStpMstVlanTable {
      description
       "Description.";
      reference
       "agentStpMstTable - 1.3.6.1.4.1.6132.1.1.1.2.15.10";
      smiv2:oid 1.3.6.1.4.1.1332.1.1.5.3.24.5;

      list msanStpMstVlanEntry {
        key "dot1qVlanIndex msanStpMstId";
        description
         "Description.";
        smiv2:oid 1.3.6.1.4.1.1332.1.1.5.3.24.5.1;

        leaf dot1qVlanIndex {
          type leafref {
            path "/q-bridge:Q-BRIDGE-MIB/q-bridge:dot1qVlanCurrentTable/q-bridge:dot1qVlanCurrentEntry/q-bridge:dot1qVlanIndex";
          }
        }

        leaf msanStpMstId {
          type leafref {
            path "/iskratel-msan:ISKRATEL-MSAN-MIB/iskratel-msan:msanStpMstTable/iskratel-msan:msanStpMstEntry/iskratel-msan:msanStpMstId";
          }
        }

        leaf msanStpMstVlanRowStatus {
          type snmpv2-tc:RowStatus;
          description
           "The association status of an MSTP instance and a VLAN.
            Instance 0 is not shown.
            
            Supported values:
            active(1)      - valid association between an MSTP instance and a VLAN.
            createAndGo(4) - used to create a new association between an MSTP instance and a VLAN.
            destroy(6)     - removes the association between an MSTP instance and a VLAN.";
          smiv2:max-access read-write;
          smiv2:oid 1.3.6.1.4.1.1332.1.1.5.3.24.5.1.1;
        }
      }
    }

    container msanStpMstPortTable {
      description
       "MST port table.";
      reference
       "agentStpMstPortTable - 1.3.6.1.4.1.6132.1.1.1.2.15.11";
      smiv2:oid 1.3.6.1.4.1.1332.1.1.5.3.24.6;

      list msanStpMstPortEntry {
        key "ifIndex msanStpMstId";
        description
         "MST port entry.";
        smiv2:oid 1.3.6.1.4.1.1332.1.1.5.3.24.6.1;

        leaf ifIndex {
          type leafref {
            path "/if-mib:interfaces/if-mib:ifEntry/if-mib:ifIndex";
          }
        }

        leaf msanStpMstId {
          type leafref {
            path "/iskratel-msan:ISKRATEL-MSAN-MIB/iskratel-msan:msanStpMstTable/iskratel-msan:msanStpMstEntry/iskratel-msan:msanStpMstId";
          }
        }

        leaf msanStpMstPortPathCost {
          type uint32 {
            range "0..200000000";
          }
          description
           "The MSTP port path cost in a specific instance. The default value will
            correspond to the recommendation specified in IEEE 802.1s Table 13-2
            which varies depending upon link speed.
            Instance 0 is not shown.";
          smiv2:max-access read-write;
          smiv2:oid 1.3.6.1.4.1.1332.1.1.5.3.24.6.1.1;
        }

        leaf msanStpMstPortPriority {
          type uint32 {
            range "0..240";
          }
          description
           "The MSTP port priority in a specific instance. The priority is
            in the increments of 16. The default value is 128.
            Instance 0 is not shown.";
          smiv2:defval 128;
          smiv2:max-access read-write;
          smiv2:oid 1.3.6.1.4.1.1332.1.1.5.3.24.6.1.2;
        }
      }
    }

    container msanStpPortTable {
      description
       "Description.";
      smiv2:oid 1.3.6.1.4.1.1332.1.1.5.3.24.7;

      list msanStpPortEntry {
        key ifIndex;
        description
         "Description.";
        smiv2:oid 1.3.6.1.4.1.1332.1.1.5.3.24.7.1;

        leaf ifIndex {
          type leafref {
            path "/if-mib:interfaces/if-mib:ifEntry/if-mib:ifIndex";
          }
        }

        leaf msanStpPortHelloTime {
          type int32 {
            range "0..10";
          }
          description
           "Hello time for the STP port. The default value is 0 (Not configured).";
          smiv2:max-access read-write;
          smiv2:oid 1.3.6.1.4.1.1332.1.1.5.3.24.7.1.1;
        }
      }
    }

    container msanStpCstPortTable {
      description
       "Description.";
      smiv2:oid 1.3.6.1.4.1.1332.1.1.5.3.24.8;

      list msanStpCstPortEntry {
        key ifIndex;
        description
         "Description.";
        smiv2:oid 1.3.6.1.4.1.1332.1.1.5.3.24.8.1;

        leaf ifIndex {
          type leafref {
            path "/if-mib:interfaces/if-mib:ifEntry/if-mib:ifIndex";
          }
        }

        leaf msanStpCstPortPathCost {
          type uint32 {
            range "0..200000000";
          }
          description
           "The MSTP port path cost in CIST. The default value will
            correspond to the recommendation specified in IEEE 802.1s Table 13-2
            which varies depending upon link speed.";
          smiv2:max-access read-write;
          smiv2:oid 1.3.6.1.4.1.1332.1.1.5.3.24.8.1.1;
        }

        leaf msanStpCstExtPortPathCost {
          type uint32 {
            range "0..200000000";
          }
          description
           "The MSTP external port path cost in CIST. The default value varies depending upon the link speed.";
          smiv2:max-access read-write;
          smiv2:oid 1.3.6.1.4.1.1332.1.1.5.3.24.8.1.2;
        }
      }
    }

    container msanAuthenticationListTable {
      description
       "Description.";
      smiv2:oid 1.3.6.1.4.1.1332.1.1.5.3.25.3;

      list msanAuthenticationListEntry {
        key msanAuthenticationListName;
        description
         "Description.";
        smiv2:oid 1.3.6.1.4.1.1332.1.1.5.3.25.3.1;

        leaf msanAuthenticationListName {
          type rfc1213-mib:DisplayString {
            length "1..15";
          }
          description
           "Authenticaiton List Name
            Unique name used to identify the Authentication List from other tables.";
          smiv2:max-access not-accessible;
          smiv2:oid 1.3.6.1.4.1.1332.1.1.5.3.25.3.1.1;
        }

        leaf msanAuthenticationListMethod1 {
          type enumeration {
            enum local {
              value 1;
            }
            enum radius {
              value 2;
            }
            enum reject {
              value 3;
            }
            enum tacacs {
              value 4;
            }
          }
          description
           "Authenticion List Method 1
            Configures the first authentication method to use when this list is
            specified.";
          smiv2:max-access read-write;
          smiv2:oid 1.3.6.1.4.1.1332.1.1.5.3.25.3.1.2;
        }

        leaf msanAuthenticationListMethod2 {
          type enumeration {
            enum undefined {
              value 1;
            }
            enum local {
              value 2;
            }
            enum radius {
              value 3;
            }
            enum reject {
              value 4;
            }
            enum tacacs {
              value 5;
            }
          }
          description
           "Authenticion List Method 2
            Configures the second authentication method to use when this list is
            specified.";
          smiv2:max-access read-write;
          smiv2:oid 1.3.6.1.4.1.1332.1.1.5.3.25.3.1.3;
        }

        leaf msanAuthenticationListMethod3 {
          type enumeration {
            enum undefined {
              value 1;
            }
            enum local {
              value 2;
            }
            enum radius {
              value 3;
            }
            enum reject {
              value 4;
            }
            enum tacacs {
              value 5;
            }
          }
          description
           "Authenticion List Method 3
            Configures the third authentication method to use when this list is
            specified.";
          smiv2:max-access read-write;
          smiv2:oid 1.3.6.1.4.1.1332.1.1.5.3.25.3.1.4;
        }
      }
    }

    container msanPortSecurityStatMacTable {
      description
       "Description.";
      smiv2:oid 1.3.6.1.4.1.1332.1.1.5.3.26.2;

      list msanPortSecurityStatMacEntry {
        key "msanPortSecurityStatMacIf msanPortSecurityStatMacVlanId msanPortSecurityStatMacMacAddress";
        description
         "Description.";
        smiv2:oid 1.3.6.1.4.1.1332.1.1.5.3.26.2.1;

        leaf msanPortSecurityStatMacIf {
          type int32;
          description
           "Unique numerical identification of the interface.";
          smiv2:max-access not-accessible;
          smiv2:oid 1.3.6.1.4.1.1332.1.1.5.3.26.2.1.1;
        }

        leaf msanPortSecurityStatMacVlanId {
          type int32 {
            range "1..4094";
          }
          description
           "VLAN identification.";
          smiv2:max-access not-accessible;
          smiv2:oid 1.3.6.1.4.1.1332.1.1.5.3.26.2.1.2;
        }

        leaf msanPortSecurityStatMacMacAddress {
          type yang:mac-address;
          description
           "Statically locked MAC addresses for port.";
          smiv2:max-access not-accessible;
          smiv2:oid 1.3.6.1.4.1.1332.1.1.5.3.26.2.1.3;
        }

        leaf msanPortSecurityStatMacRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.26.2.1.5;
        }
      }
    }

    container msanPortSecurityPortVlanTable {
      description
       "Description.";
      smiv2:oid 1.3.6.1.4.1.1332.1.1.5.3.26.3;

      list msanPortSecurityPortVlanEntry {
        key "ifIndex dot1qVlanIndex";
        description
         "Description.";
        smiv2:oid 1.3.6.1.4.1.1332.1.1.5.3.26.3.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanPortSecurityPortVlanDynamicLimit {
          type int32 {
            range "1..64";
          }
          description
           "The limit of dynamically learned MAC addresses  per vlan on selected port.";
          smiv2:max-access read-write;
          smiv2:oid 1.3.6.1.4.1.1332.1.1.5.3.26.3.1.1;
        }

        leaf msanPortSecurityPortVlanRowStatus {
          type snmpv2-tc:RowStatus;
          description
           "The row status object controls the creation/deletion of rows in this table.
            Its semantics are the same as those for the RowStatus textual convention specified for SNMPv2.
            For row creation use createAndWait(5).
            For row activation use active(1).
            For row deletion use destroy(6).
            
            Other values are currently not supported.";
          smiv2:max-access read-write;
          smiv2:oid 1.3.6.1.4.1.1332.1.1.5.3.26.3.1.2;
        }
      }
    }

    container msanLagDetailedConfigTable {
      description
       "A detailed table of the switch's LAG config entries. ";
      reference
       "agentLagDetailedConfigTable";
      smiv2:oid 1.3.6.1.4.1.1332.1.1.5.3.27.2;

      list msanLagDetailedConfigEntry {
        key "msanLagDetailedLagIndex msanLagDetailedIfIndex";
        description
         "Switch's LAG config entry";
        smiv2:oid 1.3.6.1.4.1.1332.1.1.5.3.27.2.1;

        leaf msanLagDetailedLagIndex {
          type int32;
          description
           "LAG index";
          smiv2:max-access not-accessible;
          smiv2:oid 1.3.6.1.4.1.1332.1.1.5.3.27.2.1.1;
        }

        leaf msanLagDetailedIfIndex {
          type int32;
          description
           "LAG port index";
          smiv2:max-access not-accessible;
          smiv2:oid 1.3.6.1.4.1.1332.1.1.5.3.27.2.1.2;
        }

        leaf msanLagDetailedPortSpeed {
          type yang:object-identifier-128;
          description
           "LAG port speed.  See agentPortType for a description and list
            of valid values.";
          smiv2:max-access read-write;
          smiv2:oid 1.3.6.1.4.1.1332.1.1.5.3.27.2.1.3;
        }

        leaf msanLagDetailedPortStatus {
          type enumeration {
            enum active {
              value 1;
            }
            enum inactive {
              value 2;
            }
          }
          description
           "LAG port status.
            
            active(1)   - Actively participating in the LAG.
            inactive(2) - Not participating in the LAG.";
          smiv2:max-access read-only;
          smiv2:oid 1.3.6.1.4.1.1332.1.1.5.3.27.2.1.4;
        }

        leaf msanLagDetailedRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.27.2.1.5;
        }
      }
    }

    container msanLagTable {
      description
       "Config table of additional LAG parameters.";
      smiv2:oid 1.3.6.1.4.1.1332.1.1.5.3.27.3;

      list msanLagEntry {
        key msanLagIndex;
        description
         "Description.";
        smiv2:oid 1.3.6.1.4.1.1332.1.1.5.3.27.3.1;

        leaf msanLagIndex {
          type int32;
          description
           "LAG index. Value corresponds to ifIndex for LAG interfaces in ifTable.";
          smiv2:max-access not-accessible;
          smiv2:oid 1.3.6.1.4.1.1332.1.1.5.3.27.3.1.1;
        }

        leaf msanLagMaxFrameSize {
          type int32;
          description
           "This object identifies the currently configured maximum frame size
            value for this LAG interface. ";
          smiv2:max-access read-write;
          smiv2:oid 1.3.6.1.4.1.1332.1.1.5.3.27.3.1.2;
        }

        leaf msanLagDVlanTagMode {
          type enumeration {
            enum enable {
              value 1;
            }
            enum disable {
              value 2;
            }
          }
          description
           "Controls the Double Vlan Tag mode on this LAG interface.";
          smiv2:max-access read-write;
          smiv2:oid 1.3.6.1.4.1.1332.1.1.5.3.27.3.1.3;
        }
      }
    }

    container msanRadiusServerConfigTable {
      description
       "Table with information about Radius Authentication Server IP
        Addresses, port numbers and shared secret";
      smiv2:oid 1.3.6.1.4.1.1332.1.1.5.3.28.2;

      list msanRadiusServerConfigEntry {
        key msanRadiusServerAddress;
        description
         "Entry consisting of configuration data for a Radius
          Authentication Server.";
        smiv2:oid 1.3.6.1.4.1.1332.1.1.5.3.28.2.1;

        leaf msanRadiusServerAddress {
          type inet:ipv4-address;
          description
           "IP Address of the configured RADIUS server.
            This object cannot be changed after creation.";
          smiv2:max-access not-accessible;
          smiv2:oid 1.3.6.1.4.1.1332.1.1.5.3.28.2.1.1;
        }

        leaf msanRadiusServerPort {
          type uint32 {
            range "0..65535";
          }
          description
           "Port number for the RADIUS server.";
          smiv2:defval 1812;
          smiv2:max-access read-write;
          smiv2:oid 1.3.6.1.4.1.1332.1.1.5.3.28.2.1.2;
        }

        leaf msanRadiusServerSecret {
          type rfc1213-mib:DisplayString {
            length "0..20";
          }
          description
           "Configured shared sercret for the RADIUS server.";
          smiv2:max-access read-write;
          smiv2:oid 1.3.6.1.4.1.1332.1.1.5.3.28.2.1.3;
        }

        leaf msanRadiusServerPrimaryMode {
          type enumeration {
            enum enable {
              value 1;
            }
            enum disable {
              value 2;
            }
          }
          description
           "Configure the RADIUS server to be the primary server. If there is any
            other server that is configured to be primary, that server is set to be
            a seconday server and this entry is set Primary.";
          smiv2:max-access read-write;
          smiv2:oid 1.3.6.1.4.1.1332.1.1.5.3.28.2.1.4;
        }

        leaf msanRadiusServerCurrentMode {
          type enumeration {
            enum yes {
              value 1;
            }
            enum no {
              value 2;
            }
          }
          description
           "Indicate if the RADIUS server is the current server in user for
            authentication.";
          smiv2:max-access read-only;
          smiv2:oid 1.3.6.1.4.1.1332.1.1.5.3.28.2.1.5;
        }

        leaf msanRadiusServerMsgAuth {
          type enumeration {
            enum enable {
              value 1;
            }
            enum disable {
              value 2;
            }
          }
          description
           "Enable or disable the message authenticator attribute for this
            RADIUS server.";
          smiv2:max-access read-write;
          smiv2:oid 1.3.6.1.4.1.1332.1.1.5.3.28.2.1.6;
        }

        leaf msanRadiusServerStatus {
          type snmpv2-tc:RowStatus;
          description
           "Creates or destroys a RADIUS Authentication server entry.
            
            active(1)       - This entry is active.
            createAndGo(4)  - Creates a new entry.
            destroy(6)      - Deletes an entry.";
          smiv2:max-access read-write;
          smiv2:oid 1.3.6.1.4.1.1332.1.1.5.3.28.2.1.7;
        }
      }
    }

    container msanNetworkDhcpClientVlanTable {
      description
       "DHCP client configuration per vlan id.";
      smiv2:oid 1.3.6.1.4.1.1332.1.1.5.3.29.2;

      list msanNetworkDhcpClientVlanEntry {
        key dot1qVlanIndex;
        description
         "Description.";
        smiv2:oid 1.3.6.1.4.1.1332.1.1.5.3.29.2.1;

        leaf dot1qVlanIndex {
          type leafref {
            path "/q-bridge:Q-BRIDGE-MIB/q-bridge:dot1qVlanCurrentTable/q-bridge:dot1qVlanCurrentEntry/q-bridge:dot1qVlanIndex";
          }
        }

        leaf msanNetworkDhcpClientVlanLocalOpt82 {
          type enumeration {
            enum enable {
              value 1;
            }
            enum disable {
              value 2;
            }
          }
          description
           "DHCP client on specified vlan adds relay agent information option into its own outgoing frames.";
          smiv2:defval disable;
          smiv2:max-access read-write;
          smiv2:oid 1.3.6.1.4.1.1332.1.1.5.3.29.2.1.1;
        }
      }
    }

    container msanPortStormControlTable {
      description
       "Description.";
      smiv2:oid 1.3.6.1.4.1.1332.1.1.5.3.30.2;

      list msanPortStormControlEntry {
        key ifIndex;
        description
         "Description.";
        smiv2:oid 1.3.6.1.4.1.1332.1.1.5.3.30.2.1;

        leaf ifIndex {
          type leafref {
            path "/if-mib:interfaces/if-mib:ifEntry/if-mib:ifIndex";
          }
        }

        leaf msanPortBroadcastControlMode {
          type enumeration {
            enum enable {
              value 1;
            }
            enum disable {
              value 2;
            }
          }
          description
           "he switch config broadcast allows you to enable or disable
            broadcast storm recovery mode. When you specify Enable for Broadcast
            Storm Recovery and the broadcast traffic on any Ethernet port exceeds
            the configured threshold, the switch blocks (discards) the broadcast
            traffic.";
          smiv2:max-access read-write;
          smiv2:oid 1.3.6.1.4.1.1332.1.1.5.3.30.2.1.1;
        }

        leaf msanPortBroadcastControlThreshold {
          type int32;
          units "packets per second";
          description
           "Specify the data rate at which broadcast storm control activates (packets per second)";
          smiv2:max-access read-write;
          smiv2:oid 1.3.6.1.4.1.1332.1.1.5.3.30.2.1.2;
        }

        leaf msanPortMulticastControlMode {
          type enumeration {
            enum enable {
              value 1;
            }
            enum disable {
              value 2;
            }
          }
          description
           "The switch config multicast allows you to enable or disable
            multicast storm recovery mode. When you specify Enable for multicast
            Storm Recovery and the multicast traffic on any Ethernet port exceeds
            the configured threshold, the switch blocks (discards) the multicast
            traffic";
          smiv2:max-access read-write;
          smiv2:oid 1.3.6.1.4.1.1332.1.1.5.3.30.2.1.3;
        }

        leaf msanPortMulticastControlThreshold {
          type int32;
          units "packets per second";
          description
           "Specify the data rate at which multicast storm control activates (packets per second)";
          smiv2:max-access read-write;
          smiv2:oid 1.3.6.1.4.1.1332.1.1.5.3.30.2.1.4;
        }

        leaf msanPortUnicastControlMode {
          type enumeration {
            enum enable {
              value 1;
            }
            enum disable {
              value 2;
            }
          }
          description
           "The switch config unicast allows you to enable or disable
            unicast storm recovery mode. When you specify Enable for unicast
            Storm Recovery and the unknown unicast traffic on any Ethernet port exceeds
            the configured threshold, the switch blocks (discards) the unknown unicast
            traffic.";
          smiv2:max-access read-write;
          smiv2:oid 1.3.6.1.4.1.1332.1.1.5.3.30.2.1.5;
        }

        leaf msanPortUnicastControlThreshold {
          type int32;
          units "packets per second";
          description
           "Specify the data rate at which unicast storm control activates (packets per second)";
          smiv2:max-access read-write;
          smiv2:oid 1.3.6.1.4.1.1332.1.1.5.3.30.2.1.6;
        }
      }
    }

    container msanUserConfigTable {
      description
       "Description.";
      smiv2:oid 1.3.6.1.4.1.1332.1.1.5.3.31.2;

      list msanUserConfigEntry {
        key msanUserIndex;
        description
         "Description.";
        smiv2:oid 1.3.6.1.4.1.1332.1.1.5.3.31.2.1;

        leaf msanUserIndex {
          type int32;
          description
           "User Config Index";
          smiv2:max-access not-accessible;
          smiv2:oid 1.3.6.1.4.1.1332.1.1.5.3.31.2.1.1;
        }

        leaf msanUserAccessMode {
          type enumeration {
            enum read {
              value 1;
            }
            enum write {
              value 2;
            }
          }
          description
           "User Access Mode";
          smiv2:max-access read-write;
          smiv2:oid 1.3.6.1.4.1.1332.1.1.5.3.31.2.1.2;
        }
      }
    }

    container msanSfpInfoTable {
      description
       "Description.";
      smiv2:oid 1.3.6.1.4.1.1332.1.1.5.3.32.2;

      list msanSfpInfoEntry {
        key ifIndex;
        description
         "Description.";
        smiv2:oid 1.3.6.1.4.1.1332.1.1.5.3.32.2.1;

        leaf ifIndex {
          type leafref {
            path "/if-mib:interfaces/if-mib:ifEntry/if-mib:ifIndex";
          }
        }

        leaf msanSfpInfoState {
          type enumeration {
            enum adminOff {
              value 1;
            }
            enum operational {
              value 2;
            }
            enum operWithAl {
              value 3;
            }
            enum loss {
              value 4;
            }
            enum notAvaliable {
              value 5;
            }
            enum presNoDiag {
              value 6;
            }
            enum notPresent {
              value 7;
            }
          }
          description
           "Module state value on port. Ports which support SFP module are from
            1 to 10 and from 15 to 28. State value adminOff means that specific
            port is administrative disabled and we can not read data from module
            on that port. Operational state means that SFP module is present and
            it works perfect. State operWithAl(operational with alarm) means
            that SFP module is present, but it works with internal alarms.
            Loss(Loss of signal) state means that SFP module is present but it
            have loss of signal. PresNoDiag(Present, no diagnostic) state means
            that SFP module is present but diagnostic is not supported.
            NotAvaliable state means that admin. mode of specific port has
            disabled value and SFP state is not avaliable.
            NotPresent state means that SFP module is not present.";
          smiv2:max-access read-only;
          smiv2:oid 1.3.6.1.4.1.1332.1.1.5.3.32.2.1.1;
        }

        leaf msanSfpInfoInterfaceType {
          type enumeration {
            enum sfp {
              value 1;
            }
            enum not {
              value 2;
            }
            enum no {
              value 3;
            }
            enum ad {
              value 4;
            }
            enum xfp {
              value 5;
            }
          }
          description
           "Transceiver(module) type.
            Module type can be SFP, NOT(mudule type is not SFP),
            NO(no module on port), AD(admin. disabled port) and XFP.";
          smiv2:max-access read-only;
          smiv2:oid 1.3.6.1.4.1.1332.1.1.5.3.32.2.1.2;
        }

        leaf msanSfpInfoNominalBitrate {
          type int32;
          description
           "Module(SFP) nominal bitrate value measure in Mbit/s.
            If parameter is not available, value -1 is used.";
          smiv2:max-access read-only;
          smiv2:oid 1.3.6.1.4.1.1332.1.1.5.3.32.2.1.3;
        }

        leaf msanSfpInfoNominalRange {
          type binary;
          description
           "Module(SFP) nominal range value.
            Nominal range value can support five different link lengths.
            Link length value and nominal range units are defined depends
            on value of nominal range.
            We can get link length value which can support 9/125 um fiber
            and nominal range measure  in km units.
            We can get link length value which can support 9/125 um fiber
            and nominal range measure in 100m units.
            We can get link length value which can support 50/125 um fiber
            and nominal range measure in 10m units.
            We can get link length value which can support 62,5/125 um fiber
            and nominal range measure in 10m units.
            We can get link length value which can support cooper
            and nominal range measure in m units. ";
          smiv2:max-access read-only;
          smiv2:oid 1.3.6.1.4.1.1332.1.1.5.3.32.2.1.4;
        }

        leaf msanSfpInfoVendor {
          type binary;
          description
           "Module(SFP) vendor name.";
          smiv2:max-access read-only;
          smiv2:oid 1.3.6.1.4.1.1332.1.1.5.3.32.2.1.5;
        }

        leaf msanSfpInfoIeeeVendorId {
          type int32;
          description
           "Module(SFP) vendor IEEE company ID.
            If parameter is not available, value -1 is used.";
          smiv2:max-access read-only;
          smiv2:oid 1.3.6.1.4.1.1332.1.1.5.3.32.2.1.6;
        }

        leaf msanSfpInfoPartNr {
          type binary;
          description
           "Module(SFP) part number.";
          smiv2:max-access read-only;
          smiv2:oid 1.3.6.1.4.1.1332.1.1.5.3.32.2.1.7;
        }

        leaf msanSfpInfoRevisionNr {
          type binary;
          description
           "Module(SFP) revision number.";
          smiv2:max-access read-only;
          smiv2:oid 1.3.6.1.4.1.1332.1.1.5.3.32.2.1.8;
        }

        leaf msanSfpInfoSerialNr {
          type binary;
          description
           "Module(SFP) serial number.";
          smiv2:max-access read-only;
          smiv2:oid 1.3.6.1.4.1.1332.1.1.5.3.32.2.1.9;
        }

        leaf msanSfpInfoManufacturingDate {
          type binary;
          description
           "Module(SFP) manufacturing date.";
          smiv2:max-access read-only;
          smiv2:oid 1.3.6.1.4.1.1332.1.1.5.3.32.2.1.10;
        }

        leaf msanSfpInfoWavelength {
          type int32;
          description
           "Module(SFP) laser wavelength measure in nanometers.
            If parameter is not available, value -1 is used.";
          smiv2:max-access read-only;
          smiv2:oid 1.3.6.1.4.1.1332.1.1.5.3.32.2.1.11;
        }
      }
    }

    container msanSfpDiagnosticsTable {
      description
       "Description.";
      smiv2:oid 1.3.6.1.4.1.1332.1.1.5.3.32.3;

      list msanSfpDiagnosticsEntry {
        key ifIndex;
        description
         "Description.";
        smiv2:oid 1.3.6.1.4.1.1332.1.1.5.3.32.3.1;

        leaf ifIndex {
          type leafref {
            path "/if-mib:interfaces/if-mib:ifEntry/if-mib:ifIndex";
          }
        }

        leaf msanSfpDiagnosticsSignal {
          type enumeration {
            enum loss {
              value 1;
            }
            enum ok {
              value 2;
            }
            enum notSupported {
              value 3;
            }
          }
          description
           "Module(SFP) signal value.
            If diagnostic for SFP module is supported than value can be
            OK(signal is ok) or loss(loss of signal), in the other case
            the value is set on notSupported becouse diagnostic is not
            supported(-1).";
          smiv2:max-access read-only;
          smiv2:oid 1.3.6.1.4.1.1332.1.1.5.3.32.3.1.1;
        }

        leaf msanSfpDiagnosticsTempCurrent {
          type int32;
          description
           "Current SFP module temperature value in [deg C].
            If diagnostic is not supported for SFP module then
            current temperature is set on not supported value(-129). ";
          smiv2:max-access read-only;
          smiv2:oid 1.3.6.1.4.1.1332.1.1.5.3.32.3.1.2;
        }

        leaf msanSfpDiagnosticsTempMin {
          type int32;
          description
           "SFP module minimum temperature threshold limit in [deg C].
            If diagnostic is not supported for SFP module then minimum
            temperature threshold limit is set on not supported value(-129). ";
          smiv2:max-access read-only;
          smiv2:oid 1.3.6.1.4.1.1332.1.1.5.3.32.3.1.3;
        }

        leaf msanSfpDiagnosticsTempMax {
          type int32;
          description
           "SFP module maximum temperature threshold limit in [deg C].
            If diagnostic is not supported for SFP module then maximum
            temperature threshold limit is set on not supported value(-129). ";
          smiv2:max-access read-only;
          smiv2:oid 1.3.6.1.4.1.1332.1.1.5.3.32.3.1.4;
        }

        leaf msanSfpDiagnosticsVoltageCurrent {
          type int32;
          units "0.01 V";
          description
           "Current SFP module supply voltage value in [V].
            If diagnostic is not supported for SFP module then
            current supply voltage is set on not supported value(-1). ";
          smiv2:max-access read-only;
          smiv2:oid 1.3.6.1.4.1.1332.1.1.5.3.32.3.1.6;
        }

        leaf msanSfpDiagnosticsVoltageMin {
          type int32;
          units "0.01 V";
          description
           "SFP module minimum supply voltage threshold limit in [V].
            If diagnostic is not supported for SFP module then minimum
            supply voltage threshold limit is set on not supported value(-1). ";
          smiv2:max-access read-only;
          smiv2:oid 1.3.6.1.4.1.1332.1.1.5.3.32.3.1.7;
        }

        leaf msanSfpDiagnosticsVoltageMax {
          type int32;
          units "0.01 V";
          description
           "SFP module maximum supply voltage threshold  limit in [V].
            If diagnostic is not supported for SFP module then maximum
            supply voltage threshold limit is set on not supported value(-1). ";
          smiv2:max-access read-only;
          smiv2:oid 1.3.6.1.4.1.1332.1.1.5.3.32.3.1.8;
        }

        leaf msanSfpDiagnosticsTxBiasCrrCurrent {
          type int32;
          units "0.01 mA";
          description
           "Current SFP module Tx Bias Current  value in [mA].
            If diagnostic is not supported for SFP module then
            current Tx Bias Current is set on not supported value(-1). ";
          smiv2:max-access read-only;
          smiv2:oid 1.3.6.1.4.1.1332.1.1.5.3.32.3.1.9;
        }

        leaf msanSfpDiagnosticsTxBiasCrrMin {
          type int32;
          units "0.01 mA";
          description
           "SFP module minimum Tx Bias Current threshold limit in [mA].
            If diagnostic is not supported for SFP module then minimum
            Tx Bias Current threshold limit is set on not supported value(-1). ";
          smiv2:max-access read-only;
          smiv2:oid 1.3.6.1.4.1.1332.1.1.5.3.32.3.1.10;
        }

        leaf msanSfpDiagnosticsTxBiasCrrMax {
          type int32;
          units "0.01 mA";
          description
           "SFP module maximum Tx Bias Current threshold  limit in [mA].
            If diagnostic is not supported for SFP module then maximum
            Tx Bias Current threshold  limit is set on not supported value(-1). ";
          smiv2:max-access read-only;
          smiv2:oid 1.3.6.1.4.1.1332.1.1.5.3.32.3.1.11;
        }

        leaf msanSfpDiagnosticsTxPowerCurrent {
          type int32;
          units "0.01 mW";
          description
           "Current SFP module transmitted optical output power value in [mW].
            If diagnostic is not supported for SFP module then current
            transmitted optical output power is set on not supported value(-1). ";
          smiv2:max-access read-only;
          smiv2:oid 1.3.6.1.4.1.1332.1.1.5.3.32.3.1.12;
        }

        leaf msanSfpDiagnosticsTxPowerMin {
          type int32;
          units "0.01 mW";
          description
           "SFP module minimum transmitted optical output power threshold limit
            in [mW]. If diagnostic is not supported for SFP module then minimum
            transmitted optical output power is set on not supported value(-1). ";
          smiv2:max-access read-only;
          smiv2:oid 1.3.6.1.4.1.1332.1.1.5.3.32.3.1.13;
        }

        leaf msanSfpDiagnosticsTxPowerMax {
          type int32;
          units "0.01 mW";
          description
           "SFP module maximum transmitted optical output power threshold  limit
            in [mW]. If diagnostic is not supported for SFP module then maximum
            transmitted optical output power is set on not supported value(-1).";
          smiv2:max-access read-only;
          smiv2:oid 1.3.6.1.4.1.1332.1.1.5.3.32.3.1.14;
        }

        leaf msanSfpDiagnosticsRxPowerCurrent {
          type int32;
          units "0.0001 mW";
          description
           "Current SFP module received optical input power value in [mW].
            If diagnostic is not supported for SFP module then current
            received optical input power is set on not supported value(-1). ";
          smiv2:max-access read-only;
          smiv2:oid 1.3.6.1.4.1.1332.1.1.5.3.32.3.1.15;
        }

        leaf msanSfpDiagnosticsRxPowerMin {
          type int32;
          units "0.0001 mW";
          description
           "SFP module minimum received optical input power threshold limit
            in [mW]. If diagnostic is not supported for SFP module then minimum
            received optical input power is set on not supported value(-1). ";
          smiv2:max-access read-only;
          smiv2:oid 1.3.6.1.4.1.1332.1.1.5.3.32.3.1.16;
        }

        leaf msanSfpDiagnosticsRxPowerMax {
          type int32;
          units "0.0001 mW";
          description
           "SFP module maximum received optical input power threshold  limit
            in [mW]. If diagnostic is not supported for SFP module then maximum
            received optical input power is set on not supported value(-1). ";
          smiv2:max-access read-only;
          smiv2:oid 1.3.6.1.4.1.1332.1.1.5.3.32.3.1.17;
        }

        leaf msanSfpDiagnosticsTempStatus {
          type enumeration {
            enum sfpDiagNoAlarm {
              value 1;
            }
            enum sfpDiagAlarm {
              value 2;
            }
            enum notAvailable {
              value 3;
            }
          }
          description
           "Temperature alarm status.";
          smiv2:max-access read-only;
          smiv2:oid 1.3.6.1.4.1.1332.1.1.5.3.32.3.1.19;
        }

        leaf msanSfpDiagnosticsVoltageStatus {
          type enumeration {
            enum sfpDiagNoAlarm {
              value 1;
            }
            enum sfpDiagAlarm {
              value 2;
            }
            enum notAvailable {
              value 3;
            }
          }
          description
           "Voltage alarm status.";
          smiv2:max-access read-only;
          smiv2:oid 1.3.6.1.4.1.1332.1.1.5.3.32.3.1.20;
        }

        leaf msanSfpDiagnosticsTxBiasStatus {
          type enumeration {
            enum sfpDiagNoAlarm {
              value 1;
            }
            enum sfpDiagAlarm {
              value 2;
            }
            enum notAvailable {
              value 3;
            }
          }
          description
           "TX bias alarm status.";
          smiv2:max-access read-only;
          smiv2:oid 1.3.6.1.4.1.1332.1.1.5.3.32.3.1.21;
        }

        leaf msanSfpDiagnosticsTxPowerStatus {
          type enumeration {
            enum sfpDiagNoAlarm {
              value 1;
            }
            enum sfpDiagAlarm {
              value 2;
            }
            enum notAvailable {
              value 3;
            }
          }
          description
           "TX power alarm status.";
          smiv2:max-access read-only;
          smiv2:oid 1.3.6.1.4.1.1332.1.1.5.3.32.3.1.22;
        }

        leaf msanSfpDiagnosticsRxPowerStatus {
          type enumeration {
            enum sfpDiagNoAlarm {
              value 1;
            }
            enum sfpDiagAlarm {
              value 2;
            }
            enum notAvailable {
              value 3;
            }
          }
          description
           "RX power alarm status.";
          smiv2:max-access read-only;
          smiv2:oid 1.3.6.1.4.1.1332.1.1.5.3.32.3.1.23;
        }
      }
    }

    container msanMacSgPortTable {
      description
       "Description.";
      smiv2:oid 1.3.6.1.4.1.1332.1.1.5.3.34.2;

      list msanMacSgPortEntry {
        key ifIndex;
        description
         "Description.";
        smiv2:oid 1.3.6.1.4.1.1332.1.1.5.3.34.2.1;

        leaf ifIndex {
          type leafref {
            path "/if-mib:interfaces/if-mib:ifEntry/if-mib:ifIndex";
          }
        }

        leaf msanMacSgPortStatus {
          type enumeration {
            enum enable {
              value 1;
            }
            enum disable {
              value 2;
            }
          }
          description
           "Administrative state of MAC Source Guard on interface.";
          smiv2:max-access read-write;
          smiv2:oid 1.3.6.1.4.1.1332.1.1.5.3.34.2.1.1;
        }

        leaf msanMacSgPortViolationsCounter {
          type int32;
          description
           "MAC Source Guard Violations counter";
          smiv2:max-access read-only;
          smiv2:oid 1.3.6.1.4.1.1332.1.1.5.3.34.2.1.2;
        }
      }
    }

    container msanErrorDisablePortTable {
            config false;

      description
       "Description.";
      smiv2:oid 1.3.6.1.4.1.1332.1.1.5.3.35.2;

      list msanErrorDisablePortEntry {
        key ifName;
        description
         "Description.";
        smiv2:oid 1.3.6.1.4.1.1332.1.1.5.3.35.2.1;

        leaf ifName {
          type if:interface-state-ref ;
                    description 
                        "A reference to the name of a configured network layer
                         interface.";

        }

        leaf msanErrorDisablePortStatus {
          type enumeration {
            enum regular {
              value 1;
            }
            enum errorDisable {
              value 2;
            }
          }
          description
           "This parameter shows which interfaces are in errorDisable(2)
            recovery administrative state.";
          smiv2:max-access read-only;
          smiv2:oid 1.3.6.1.4.1.1332.1.1.5.3.35.2.1.1;
        }

        leaf msanErrorDisablePortCause {
          type binary;
          description
           "Cause for errorDisable(2) status on interface.";
          smiv2:max-access read-only;
          smiv2:oid 1.3.6.1.4.1.1332.1.1.5.3.35.2.1.2;
        }

        leaf msanErrorDisablePortTimeLeft {
          type int32;
          units sec;
          description
           "Time in seconds which defines how much time left for
            interface to stay in errorDisable(2) state.";
          smiv2:max-access read-only;
          smiv2:oid 1.3.6.1.4.1.1332.1.1.5.3.35.2.1.3;
        }

        leaf msanErrorDisablePortCounter {
          type int32;
          description
           "The number of times the specified interface has been in errorDisable(2) state.";
          smiv2:max-access read-only;
          smiv2:oid 1.3.6.1.4.1.1332.1.1.5.3.35.2.1.4;
        }
      }
    }

    container msanAdslAtucPhysExtnTable {
      description
       "This table provides one row for each ATUC. This table is an extention to adslAtucPhysTable defined in rfc-2662.";
      smiv2:oid 1.3.6.1.4.1.1332.1.1.5.3.36.2;

      list msanAdslAtucPhysExtnEntry {
        key ifIndex;
        description
         "An entry (conceptual row) in the msanAdslAtucPhysExtnTable.
          The Table is indexed by ifIndex.";
        smiv2:oid 1.3.6.1.4.1.1332.1.1.5.3.36.2.1;

        leaf ifIndex {
          type leafref {
            path "/if-mib:interfaces/if-mib:ifEntry/if-mib:ifIndex";
          }
        }

        leaf msanAdslAtucPhysExtnOpState {
          type enumeration {
            enum idle {
              value 0;
            }
            enum data {
              value 1;
            }
            enum bootupLoad {
              value 8;
            }
            enum handshake {
              value 16;
            }
            enum training {
              value 24;
            }
            enum framerSync {
              value 26;
            }
            enum fastRetrainInProg {
              value 27;
            }
            enum discovery {
              value 46;
            }
            enum llTest {
              value 128;
            }
            enum dlTest {
              value 131;
            }
            enum txTest {
              value 132;
            }
            enum atmLpTest {
              value 133;
            }
            enum deltTraining {
              value 139;
            }
            enum delt {
              value 140;
            }
          }
          description
           "This object indicates the operational state of the ATU. Values include idle, handshake, training, etc.";
          smiv2:max-access read-only;
          smiv2:oid 1.3.6.1.4.1.1332.1.1.5.3.36.2.1.1;
        }

        leaf msanAdslAtucPhysExtnActualStd {
          type enumeration {
            enum t1413 {
              value 0;
            }
            enum gLite {
              value 1;
            }
            enum gDmt {
              value 2;
            }
            enum alctl14 {
              value 3;
            }
            enum multimode {
              value 4;
            }
            enum adi {
              value 5;
            }
            enum alctl {
              value 6;
            }
            enum t1413auto {
              value 9;
            }
            enum adsl2 {
              value 26;
            }
            enum adsl2Plus {
              value 27;
            }
            enum readsl2 {
              value 28;
            }
            enum adsl2Auto {
              value 29;
            }
            enum adsl2PlusAuto {
              value 30;
            }
            enum adslPlus {
              value 48;
            }
            enum gspanPlus {
              value 64;
            }
            enum gspanPlusPlus {
              value 80;
            }
          }
          description
           "This object provides actual ATU-C configuration based on outcome of negotiation with ATU-R. In this case, the parameter provides actual standard used for the connection.";
          smiv2:max-access read-only;
          smiv2:oid 1.3.6.1.4.1.1332.1.1.5.3.36.2.1.2;
        }

        leaf msanAdslAtucPhysExtnBertError {
          type int32;
          description
           "This object indicates the No. of bit errors detected during BERT.";
          smiv2:max-access read-only;
          smiv2:oid 1.3.6.1.4.1.1332.1.1.5.3.36.2.1.3;
        }

        leaf msanAdslAtucPhysExtnTxAtmCellCounter {
          type yang:counter32;
          description
           "This object Provides transmit ATM cell counter.";
          smiv2:max-access read-only;
          smiv2:oid 1.3.6.1.4.1.1332.1.1.5.3.36.2.1.4;
        }

        leaf msanAdslAtucPhysExtnRxAtmCellCounter {
          type int32;
          description
           "This object Provides receive ATM cell counter.";
          smiv2:max-access read-only;
          smiv2:oid 1.3.6.1.4.1.1332.1.1.5.3.36.2.1.5;
        }

        leaf msanAdslAtucPhysExtnStartProgress {
          type int32;
          description
           "This object provides current detailed start up information to be used for debugging.";
          smiv2:max-access read-only;
          smiv2:oid 1.3.6.1.4.1.1332.1.1.5.3.36.2.1.6;
        }

        leaf msanAdslAtucPhysExtnIdleBertError {
          type int32;
          description
           "Number of bit errors.";
          smiv2:max-access read-only;
          smiv2:oid 1.3.6.1.4.1.1332.1.1.5.3.36.2.1.7;
        }

        leaf msanAdslAtucPhysExtnIdleBertCells {
          type int32;
          description
           "Number of idle cells.";
          smiv2:max-access read-only;
          smiv2:oid 1.3.6.1.4.1.1332.1.1.5.3.36.2.1.8;
        }

        leaf msanAdslAtucPhysExtnBertSync {
          type enumeration {
            enum bertOutOfSync {
              value 0;
            }
            enum bertInSync {
              value 128;
            }
          }
          description
           "Indicates if the Signal is in Sync or not.";
          smiv2:max-access read-only;
          smiv2:oid 1.3.6.1.4.1.1332.1.1.5.3.36.2.1.9;
        }

        leaf msanAdslAtucPhysExtnParametricTestResult {
          type enumeration {
            enum ok {
              value 0;
            }
            enum fail {
              value 1;
            }
            enum dspIfFail {
              value 2;
            }
          }
          description
           "Indicates the Result of the Parametric Test conducted on the Xcvr.";
          smiv2:max-access read-only;
          smiv2:oid 1.3.6.1.4.1.1332.1.1.5.3.36.2.1.10;
        }

        leaf msanAdslAtucPhysExtnSeltInfoValid {
          type enumeration {
            enum true {
              value 1;
            }
            enum notConnected {
              value 32768;
            }
            enum lostConnection {
              value 33024;
            }
            enum noResponseSeltEngine {
              value 33280;
            }
          }
          description
           "Indicates the information validity for the SELT operation conducted on the Xcvr.";
          smiv2:max-access read-only;
          smiv2:oid 1.3.6.1.4.1.1332.1.1.5.3.36.2.1.11;
        }

        leaf msanAdslAtucPhysExtnSeltLoopLen {
          type int32;
          description
           "Indicates the LOOP Length in Feet once when the SELT information is valid on the Xcvr.";
          smiv2:max-access read-only;
          smiv2:oid 1.3.6.1.4.1.1332.1.1.5.3.36.2.1.12;
        }

        leaf msanAdslAtucPhysExtnSeltLoopEnd {
          type enumeration {
            enum open {
              value 0;
            }
            enum short {
              value 1;
            }
            enum unknown {
              value 2;
            }
          }
          description
           "Indicates whether the loop is short or open once when the SELT information is valid on the Xcvr.";
          smiv2:max-access read-only;
          smiv2:oid 1.3.6.1.4.1.1332.1.1.5.3.36.2.1.13;
        }

        leaf msanAdslAtucPhysExtnSeltLoopGauge {
          type enumeration {
            enum greater26awg {
              value -1;
            }
            enum equal26awg {
              value 0;
            }
            enum equal24awg {
              value 1;
            }
            enum less26awg {
              value 2;
            }
            enum unknownAwg {
              value 3;
            }
          }
          description
           "Indicates the LOOP wire_gauge information once when the SELT information is valid on the Xcvr.";
          smiv2:max-access read-only;
          smiv2:oid 1.3.6.1.4.1.1332.1.1.5.3.36.2.1.14;
        }

        leaf msanAdslAtucPhysExtnSeltUpShannonCap {
          type yang:gauge32;
          description
           "Indicates the LOOP Upstream Shannon Capacity (in bps) once when the SELT information is valid on the Xcvr.";
          smiv2:max-access read-only;
          smiv2:oid 1.3.6.1.4.1.1332.1.1.5.3.36.2.1.15;
        }

        leaf msanAdslAtucPhysExtnSeltDownShannonCap {
          type yang:gauge32;
          description
           "Indicates the LOOP Downstream Shannon Capacity (in bps) once when the SELT information is valid on the Xcvr.";
          smiv2:max-access read-only;
          smiv2:oid 1.3.6.1.4.1.1332.1.1.5.3.36.2.1.16;
        }

        leaf msanAdslAtucPhysExtnSeltInbandNoise {
          type binary {
            length "0..2048";
          }
          description
           "512 values that indicate inband noise length in dBM/Hz, covering both bands from 0 to 1.1 MHz.";
          smiv2:max-access read-only;
          smiv2:oid 1.3.6.1.4.1.1332.1.1.5.3.36.2.1.17;
        }

        leaf msanAdslAtucPhysExtnSeltTerminationResp {
          type binary {
            length "0..720";
          }
          description
           "180 discrete values that indicate termination response magnitude from 0 to 18Kft.";
          smiv2:max-access read-only;
          smiv2:oid 1.3.6.1.4.1.1332.1.1.5.3.36.2.1.18;
        }

        leaf msanAdslAtucPhysExtnSeltUpMgnAtRate {
          type binary {
            length "0..1200";
          }
          description
           "300 values that indicate SNR margin in dB/10 at a particular rate are provided, at 100K increments, up to 15 Mbps.";
          smiv2:max-access read-only;
          smiv2:oid 1.3.6.1.4.1.1332.1.1.5.3.36.2.1.19;
        }

        leaf msanAdslAtucPhysExtnSeltDownMgnAtRate {
          type binary {
            length "0..1200";
          }
          description
           "300 values that indicate SNR margin in dB/10 at a particular rate are provided, at 100K increments, up to 15 Mbps.";
          smiv2:max-access read-only;
          smiv2:oid 1.3.6.1.4.1.1332.1.1.5.3.36.2.1.20;
        }

        leaf msanAdslAtucPhysExtnDataBoostStatus {
          type enumeration {
            enum disabled {
              value 0;
            }
            enum enabled {
              value 32768;
            }
          }
          description
           "This object indicates whether DataBoost is utilized for the connection.";
          smiv2:max-access read-only;
          smiv2:oid 1.3.6.1.4.1.1332.1.1.5.3.36.2.1.21;
        }

        leaf msanAdslAtucPhysExtnTestArray {
          type binary {
            length "0..1024";
          }
          description
           "This object indicates the Parametric Test Array. Every Four octets refer to one element in this array of octets.";
          smiv2:max-access read-only;
          smiv2:oid 1.3.6.1.4.1.1332.1.1.5.3.36.2.1.22;
        }

        leaf msanAdslAtucPhysExtnChanPerfCD {
          type int32;
          description
           "The near-end delineated total cell count performance parameter is a count of the total number of cells passed through the cell delineation and HEC function process operating on the ATM Data Path while in the SYNC state. (Not available for ADSL).";
          smiv2:max-access read-only;
          smiv2:oid 1.3.6.1.4.1.1332.1.1.5.3.36.2.1.23;
        }

        leaf msanAdslAtucPhysExtnChanPerfBE {
          type int32;
          description
           "The near-end idle bit error count performance parameter is a count of the number of bit errors in the idle cell payload received in the ATM Data Path at the near-end. (Not available for ADSL).";
          smiv2:max-access read-only;
          smiv2:oid 1.3.6.1.4.1.1332.1.1.5.3.36.2.1.24;
        }

        leaf msanAdslAtucPhysExtnDeltHLINSCus {
          type int32;
          description
           "DELT-related parameter that provides the scale factor to be applied to the upstream Hlin(f) values.(Not available for ADSL and ADSL2plus).";
          smiv2:max-access read-only;
          smiv2:oid 1.3.6.1.4.1.1332.1.1.5.3.36.2.1.25;
        }

        leaf msanAdslAtucPhysExtnDeltHLINpsus {
          type binary {
            length "0..128";
          }
          description
           "DELT-related parameter that provides an array of complex upstream Hlin(f) values in linear scale. (Not available for ADSL and ADSL2plus).  Every two octets refer to one element in this array of octets.";
          smiv2:max-access read-only;
          smiv2:oid 1.3.6.1.4.1.1332.1.1.5.3.36.2.1.26;
        }

        leaf msanAdslAtucPhysExtnDeltHLOGMTus {
          type int32;
          description
           "DELT-related parameter that provides the number of symbols used to measure the upstream Hlog(f).(Not available for ADSL and ADSL2plus).";
          smiv2:max-access read-only;
          smiv2:oid 1.3.6.1.4.1.1332.1.1.5.3.36.2.1.27;
        }

        leaf msanAdslAtucPhysExtnDeltHLOGpsus {
          type binary {
            length "0..64";
          }
          description
           "DELT-related parameter that provides an array of real upstream Hlog(f) values in dB. (Not available for ADSL and ADSL2plus). Every two octets refer to one element in this array of octets.";
          smiv2:max-access read-only;
          smiv2:oid 1.3.6.1.4.1.1332.1.1.5.3.36.2.1.28;
        }

        leaf msanAdslAtucPhysExtnDeltQLNMTus {
          type int32;
          description
           "DELT-related parameter that provides the number of symbols used to measure the upstream QLN(f) values. (Not available for ADSL and ADSL2plus).";
          smiv2:max-access read-only;
          smiv2:oid 1.3.6.1.4.1.1332.1.1.5.3.36.2.1.29;
        }

        leaf msanAdslAtucPhysExtnDeltQLNpsus {
          type binary {
            length "0..32";
          }
          description
           "DELT-related parameter that provides an array of real upstream QLN(f) values in dB. (Not available for ADSL and ADSL2plus). Every two octets refer to one element in this array of octets.";
          smiv2:max-access read-only;
          smiv2:oid 1.3.6.1.4.1.1332.1.1.5.3.36.2.1.30;
        }

        leaf msanAdslAtucPhysExtnDeltLastTxState {
          type enumeration {
            enum dmtatucg9941 {
              value 0;
            }
            enum dmtatucquiet1 {
              value 1;
            }
            enum dmtatuccomb1 {
              value 2;
            }
            enum dmtatucquiet2 {
              value 3;
            }
            enum dmtatuccomb2 {
              value 4;
            }
            enum dmtatucicomb1 {
              value 5;
            }
            enum dmtatuclineprob {
              value 6;
            }
            enum dmtatucquiet3 {
              value 7;
            }
            enum dmtatuccomb3 {
              value 8;
            }
            enum dmtatucicomb2 {
              value 9;
            }
            enum dmtatucmsgfmt {
              value 10;
            }
            enum dmtatucmsgpcb {
              value 11;
            }
            enum dmtatucquiet4 {
              value 12;
            }
            enum dmtatucreverb1 {
              value 13;
            }
            enum dmtatuctref1 {
              value 14;
            }
            enum dmtatucreverb2 {
              value 15;
            }
            enum dmtatucect {
              value 16;
            }
            enum dmtatucreverb3 {
              value 17;
            }
            enum dmtatuctref2 {
              value 18;
            }
            enum dmtatucreverb4 {
              value 19;
            }
            enum dmtatucsegue1 {
              value 20;
            }
            enum dmtatucmsg1 {
              value 21;
            }
            enum dmtatucreverb5 {
              value 22;
            }
            enum dmtatucsegue2 {
              value 23;
            }
            enum dmtatucmedley {
              value 24;
            }
            enum dmtatucexchmarker {
              value 25;
            }
            enum dmtatucmsg2 {
              value 26;
            }
            enum dmtatucreverb6 {
              value 27;
            }
            enum dmtatucsegue3 {
              value 28;
            }
            enum dmtatucparams {
              value 29;
            }
            enum dmtatucreverb7 {
              value 30;
            }
            enum dmtatucsegue4 {
              value 31;
            }
            enum dmtatucshowtime {
              value 32;
            }
          }
          description
           "DELT-related parameter that provides last successful transmitted initialization state by the ATU-C. (Not available for ADSL and ADSL2plus).";
          smiv2:max-access read-only;
          smiv2:oid 1.3.6.1.4.1.1332.1.1.5.3.36.2.1.31;
        }

        leaf msanAdslAtucPhysExtnPMState {
          type enumeration {
            enum l0 {
              value 0;
            }
            enum l2 {
              value 2;
            }
            enum l3 {
              value 3;
            }
          }
          description
           "Line Power Management State. (Not available for ADSL).";
          smiv2:max-access read-only;
          smiv2:oid 1.3.6.1.4.1.1332.1.1.5.3.36.2.1.32;
        }

        leaf msanAdslAtucPhysExtnChanPerfCU {
          type int32;
          description
           " The near-end user total cell count performance parameter is a count of the total number of cells in the ATM Data Path delivered at the V-C (for ATU-C) or T-R (for ATU-R) interface. (Not available for ADSL).";
          smiv2:max-access read-only;
          smiv2:oid 1.3.6.1.4.1.1332.1.1.5.3.36.2.1.33;
        }

        leaf msanAdslAtucPhysExtnExtendedPsdStatus {
          type boolean;
          description
           "Conexant parameter that indicates whether an extended upstream PSD is used - for G.Span Plus mode of operation only. Only supported for G.Span Plus, therefore this parameter is not valid for ADSL2/ADSL2plus modes of operation.";
          smiv2:max-access read-only;
          smiv2:oid 1.3.6.1.4.1.1332.1.1.5.3.36.2.1.34;
        }

        leaf msanAdslAtucPhysExtnChipVersion {
          type int32;
          description
           "Conexant parameter that indicates the DSP version number.";
          smiv2:max-access read-only;
          smiv2:oid 1.3.6.1.4.1.1332.1.1.5.3.36.2.1.35;
        }

        leaf msanAdslAtucPhysExtnPilotTone {
          type int32;
          description
           "Conexant parameter that indicates the Pilot Tone Index.";
          smiv2:max-access read-only;
          smiv2:oid 1.3.6.1.4.1.1332.1.1.5.3.36.2.1.36;
        }

        leaf msanAdslAtucMSGds {
          type yang:gauge32;
          description
           "Indicates the Overhead Channel. This feature is not supported by DSLPHY as yet.";
          smiv2:max-access read-only;
          smiv2:oid 1.3.6.1.4.1.1332.1.1.5.3.36.2.1.37;
        }

        leaf msanAdslAtucPhysExtnPsdMaskMode {
          type enumeration {
            enum coMsk2 {
              value 0;
            }
            enum flatMsk {
              value 3;
            }
            enum cabMsk2 {
              value 4;
            }
            enum adsl2NonovlpFlat {
              value 259;
            }
            enum adsl2NonovlpM1 {
              value 275;
            }
            enum adsl2NonovlpM2 {
              value 291;
            }
            enum coMsk2Rfi {
              value 32768;
            }
            enum flatMskRfi {
              value 32771;
            }
            enum cabMsk2Rfi {
              value 32772;
            }
            enum coMsk2Rfi0 {
              value 49152;
            }
          }
          description
           "Conexant parameter that indicates the actual Psd Mask currently being used.";
          smiv2:max-access read-only;
          smiv2:oid 1.3.6.1.4.1.1332.1.1.5.3.36.2.1.38;
        }

        leaf msanAdslAtucPhysExtnDeltSNRMTus {
          type int32;
          description
           "DELT-related parameter that provides the number of symbols used to measure the upstream SNR(f) values. (Not available for ADSL and ADSL2plus)";
          smiv2:max-access read-only;
          smiv2:oid 1.3.6.1.4.1.1332.1.1.5.3.36.2.1.39;
        }

        leaf msanAdslAtucPhysExtnDeltCurrStatus {
          type enumeration {
            enum failedUnknown {
              value 0;
            }
            enum failedInsufficientCapacity {
              value 17;
            }
            enum failedCrcError {
              value 34;
            }
            enum failedTimeOut {
              value 68;
            }
            enum failedUnexpectedContent {
              value 136;
            }
            enum success {
              value 255;
            }
          }
          description
           "This Conexant parameter indicates the current status of Atuc Line in DELT mode.";
          smiv2:max-access read-only;
          smiv2:oid 1.3.6.1.4.1.1332.1.1.5.3.36.2.1.40;
        }

        leaf msanAdslAtucSATN {
          type int32;
          description
           "DELT-related parameter that provides the upstream signal attenuation (length = 4 bytes). (Not available for ADSL and ADSL2plus). For further details, Refer to Section 7.5.1.9 Revised Recommendation G.997.1.";
          smiv2:max-access read-only;
          smiv2:oid 1.3.6.1.4.1.1332.1.1.5.3.36.2.1.41;
        }

        leaf msanAdslAtucPhysExtnSystemVendorId {
          type binary {
            length "0..9";
          }
          description
           "Indicates the Vendor ID as inserted by the ATU-C in the Overhead Messages(ADSL2). Typically identifies the ATU-C system integrator which usually refers to the vendor of the smallest field-replaceable unit. ATU-C System Vendor ID may not be the same as ATU-C Vendor ID. It is not available for ADSL. This is string of 8 octets containing 2 octet country code , 4 octet vendor id and 2 octet vendor revision number.";
          smiv2:max-access read-only;
          smiv2:oid 1.3.6.1.4.1.1332.1.1.5.3.36.2.1.42;
        }

        leaf msanAdslAtucPhysExtnSelfTestResult {
          type yang:gauge32;
          description
           "Defines the ATU-C selftest result. The most significant octet is: 00 hex if the self-test passed or 01 hex if the self-test failed. Interpretation of the other octets is vendor discretionary and can be interpreted in combination with G.994.1 and system Vendor IDs. For further details, refer to Section 7.4.9 Revised Recommendation G.997.1.";
          smiv2:max-access read-only;
          smiv2:oid 1.3.6.1.4.1.1332.1.1.5.3.36.2.1.43;
        }

        leaf msanAdslAtucPhysExtnG9941VendorId {
          type binary {
            length "0..9";
          }
          description
           "Indicates the Vendor ID as inserted by the ATU-C in the G.994.1 CL message. Typically identifies the vendor of the ATU-C G.994.1 functionality. This is string of 8 octets containing 2 octet country code , 4 octet vendor id and 2 octet vendor revision number. For further details, refer to Section 7.4.1 Revised Recommendation G.997.1.";
          smiv2:max-access read-only;
          smiv2:oid 1.3.6.1.4.1.1332.1.1.5.3.36.2.1.44;
        }

        leaf msanAdslAtucPhysExtnTsspsUs {
          type binary {
            length "0..128";
          }
          description
           "This parameter provides the Upstream Transmit Spectrum Shaping parameter expressed as the set of break points exchanged during G994.1. Each breakpoint consists in a subcarrier index and the associated shaping parameter. Value of this parameter is in range 0 - 127, in multiples of -0.5 dB. 127 is a special value indicating the subcarrier is not transmitted. It is available only for ADSL2/ADSL2plus.For further details, Refer to Section 7.5.1.21.5 Revised Recommendation G.997.1.";
          smiv2:max-access read-only;
          smiv2:oid 1.3.6.1.4.1.1332.1.1.5.3.36.2.1.45;
        }

        leaf msanAdslAtucPhysExtnActPsdUs {
          type int32;
          description
           "This parameter defines the average upstream transmit power spectrum density over the used subcarriers delivered by the ATU-C at the U-C reference point, at the instant of measurement. It's value ranges from -90 to 0, in 0.1 dB/Hz steps. It is available only for ADSL2/ADSL2plus. For further details, Refer to Section 7.5.1.14 Revised Recommendation G.997.1.";
          smiv2:max-access read-only;
          smiv2:oid 1.3.6.1.4.1.1332.1.1.5.3.36.2.1.46;
        }

        leaf msanAdslAtucPhysExtnGainspsUs {
          type binary {
            length "0..128";
          }
          description
           "This parameter defines the upstream gains allocation table per subcarrier. It is an array of integer values in the 0 to 4093 range for subcarriers 0 to NSCus-1. The gain value is represented as a multiple of 1/512 on linear scale. It is supported for ADSL2/ADSl2plus only.";
          smiv2:max-access read-only;
          smiv2:oid 1.3.6.1.4.1.1332.1.1.5.3.36.2.1.47;
        }

        leaf msanAdslAtucPhysExtnStartBin {
          type int32;
          description
           "This Gspan++ parameter indicates the start bin of the bit loading up array.";
          smiv2:max-access read-only;
          smiv2:oid 1.3.6.1.4.1.1332.1.1.5.3.36.2.1.48;
        }

        leaf msanAdslAtucPhysExtnStartupErrorCode {
          type enumeration {
            enum startupErrorCodeOk {
              value 0;
            }
            enum startupErrorCodeMaxnomPsdDs {
              value 1;
            }
            enum startupErrorCodePsdMaskDs {
              value 2;
            }
            enum startupErrorCodeMaxnomAtpDs {
              value 4;
            }
            enum startupErrorCodeMaxnomPsdUs {
              value 65536;
            }
            enum startupErrorCodePsdMaskUs {
              value 131072;
            }
            enum startupErrorCodeMaxnomAtpUs {
              value 262144;
            }
          }
          description
           "Conexant parameter which indicates the startup error code.";
          smiv2:max-access read-only;
          smiv2:oid 1.3.6.1.4.1.1332.1.1.5.3.36.2.1.49;
        }

        leaf msanAdslAtucPhysExtnBitSwapCount {
          type uint32;
          description
           "This Conexant parameter indicates the bit swap count. It can read only in data mode";
          smiv2:max-access read-only;
          smiv2:oid 1.3.6.1.4.1.1332.1.1.5.3.36.2.1.50;
        }

        leaf msanAdslAtucPhysExtnModPhase {
          type enumeration {
            enum flatRateCheck {
              value 0;
            }
            enum snrMeasure {
              value 1;
            }
            enum modRateCheck {
              value 2;
            }
            enum modShowtime {
              value 3;
            }
            enum flatShowtime {
              value 4;
            }
          }
          description
           "Conexant parameter to monitor the status of MoD";
          smiv2:max-access read-only;
          smiv2:oid 1.3.6.1.4.1.1332.1.1.5.3.36.2.1.51;
        }
      }
    }

    container msanAdslLineExtnTable {
      description
       "This table includes common attributes describing both ends of the line.  It is required for all ADSL physical interfaces. This Table is an extension to adslLineTable defined in rfc-2662.";
      smiv2:oid 1.3.6.1.4.1.1332.1.1.5.3.36.3;

      list msanAdslLineExtnEntry {
        key ifIndex;
        description
         "An entry (conceptual row) in the msanAdslLineExtnTable.
          The Table is indexed by ifIndex.";
        smiv2:oid 1.3.6.1.4.1.1332.1.1.5.3.36.3.1;

        leaf ifIndex {
          type leafref {
            path "/if-mib:interfaces/if-mib:ifEntry/if-mib:ifIndex";
          }
        }

        leaf msanAdslLineExtnAction {
          type enumeration {
            enum startup {
              value 0;
            }
            enum abortReq {
              value 2;
            }
            enum spectrumReverb {
              value 5;
            }
            enum analogLb {
              value 6;
            }
            enum digitalLb {
              value 7;
            }
            enum atmLp {
              value 10;
            }
            enum spectrumMedley {
              value 26;
            }
            enum spectrumPilot {
              value 27;
            }
            enum spectrumCMtpr {
              value 30;
            }
            enum spectrumRMtpr {
              value 32;
            }
            enum shutdown {
              value 101;
            }
            enum wakeup {
              value 102;
            }
            enum selt {
              value 4134;
            }
            enum hybridLossTest {
              value 8193;
            }
            enum rcvLinearityTest {
              value 8194;
            }
            enum rcvFilterTest {
              value 8195;
            }
            enum rcvPowerPerBinTest {
              value 8196;
            }
            enum totalIdleNoiseTest {
              value 8197;
            }
            enum idleNoisePerBinTest {
              value 8198;
            }
          }
          description
           "this object indicates parameter that allows actions on a per line basis. These actions include abort, startup, and tests.";
          smiv2:max-access read-write;
          smiv2:oid 1.3.6.1.4.1.1332.1.1.5.3.36.3.1.1;
        }

        leaf msanAdslLineExtnUtopiaL2RxAddr {
          type int32 {
            range "0..254";
          }
          description
           "This object indicates UTOPIA Level 2 Rx address for a line.";
          smiv2:max-access read-only;
          smiv2:oid 1.3.6.1.4.1.1332.1.1.5.3.36.3.1.2;
        }

        leaf msanAdslLineExtnUtopiaL2TxAddr {
          type int32 {
            range "0..254";
          }
          description
           "This object indicates UTOPIA Level 2 Tx address for a line.";
          smiv2:max-access read-only;
          smiv2:oid 1.3.6.1.4.1.1332.1.1.5.3.36.3.1.3;
        }

        leaf msanAdslLineExtnTransAtucCap {
          type bits {
            bit ansit1413 {
              position 0;
            }
            bit etsi {
              position 1;
            }
            bit q9921PotsNonOverlapped {
              position 2;
            }
            bit q9921PotsOverlapped {
              position 3;
            }
            bit q9921IsdnNonOverlapped {
              position 4;
            }
            bit q9921isdnOverlapped {
              position 5;
            }
            bit q9921tcmIsdnNonOverlapped {
              position 6;
            }
            bit q9921tcmIsdnOverlapped {
              position 7;
            }
            bit q9922potsNonOverlapeed {
              position 8;
            }
            bit q9922potsOverlapped {
              position 9;
            }
            bit q9922tcmIsdnNonOverlapped {
              position 10;
            }
            bit q9922tcmIsdnOverlapped {
              position 11;
            }
            bit q9921tcmIsdnSymmetric {
              position 12;
            }
            bit adslPlusPotsNonOverlapped {
              position 13;
            }
            bit adslPlusPotsOverlapped {
              position 18;
            }
            bit q9921GspanPlusPlusPotsNonOverlapped {
              position 20;
            }
            bit q9921GspanPlusPlusPotsOverlapped {
              position 21;
            }
            bit q9923Readsl2PotsOverlapped {
              position 22;
            }
            bit q9923Readsl2PotsNonOverlapped {
              position 23;
            }
            bit vdslOverlapped {
              position 24;
            }
            bit vdslNonOverlapped {
              position 25;
            }
            bit q9925Adsl2PlusPotsNonOverlapped {
              position 26;
            }
            bit q9925Adsl2PlusPotsOverlapped {
              position 27;
            }
            bit q9923Adsl2PotsNonOverlapped {
              position 28;
            }
            bit q9923Adsl2PotsOverlapped {
              position 29;
            }
            bit q9921GspanPlusPotsOverlapped {
              position 30;
            }
            bit q9921GspanPlusPotsNonOverlapped {
              position 31;
            }
            bit q9923IsdnNonOverlapped {
              position 34;
            }
            bit q9923IsdnOverlapped {
              position 35;
            }
            bit q9925IsdnNonOverlapped {
              position 42;
            }
            bit q9925IsdnOverlapped {
              position 43;
            }
            bit q9923AnnexMPotsExtUsNonOverlapped {
              position 56;
            }
            bit q9923AnnexMPotsExtUsOverlapped {
              position 57;
            }
            bit q9925AnnexMPotsExtUsNonOverlapped {
              position 60;
            }
            bit q9925AnnexMPotsExtUsOverlapped {
              position 61;
            }
          }
          description
           "The transmission modes that the ATU-C is capable of supporting. The modes available are limited by the design of the equipment. REFERENCE Section 7.3.2 ITU G.997.1.";
          smiv2:max-access read-only;
          smiv2:oid 1.3.6.1.4.1.1332.1.1.5.3.36.3.1.4;
        }

        leaf msanAdslLineExtnTransAtucActual {
          type bits {
            bit ansit1413 {
              position 0;
            }
            bit etsi {
              position 1;
            }
            bit q9921PotsNonOverlapped {
              position 2;
            }
            bit q9921PotsOverlapped {
              position 3;
            }
            bit q9921IsdnNonOverlapped {
              position 4;
            }
            bit q9921isdnOverlapped {
              position 5;
            }
            bit q9921tcmIsdnNonOverlapped {
              position 6;
            }
            bit q9921tcmIsdnOverlapped {
              position 7;
            }
            bit q9922potsNonOverlapeed {
              position 8;
            }
            bit q9922potsOverlapped {
              position 9;
            }
            bit q9922tcmIsdnNonOverlapped {
              position 10;
            }
            bit q9922tcmIsdnOverlapped {
              position 11;
            }
            bit q9921tcmIsdnSymmetric {
              position 12;
            }
            bit adslPlusPotsNonOverlapped {
              position 13;
            }
            bit adslPlusPotsOverlapped {
              position 18;
            }
            bit q9921GspanPlusPlusPotsNonOverlapped {
              position 20;
            }
            bit q9921GspanPlusPlusPotsOverlapped {
              position 21;
            }
            bit q9923Readsl2PotsOverlapped {
              position 22;
            }
            bit q9923Readsl2PotsNonOverlapped {
              position 23;
            }
            bit vdslOverlapped {
              position 24;
            }
            bit vdslNonOverlapped {
              position 25;
            }
            bit q9925Adsl2PlusPotsNonOverlapped {
              position 26;
            }
            bit q9925Adsl2PlusPotsOverlapped {
              position 27;
            }
            bit q9923Adsl2PotsNonOverlapped {
              position 28;
            }
            bit q9923Adsl2PotsOverlapped {
              position 29;
            }
            bit q9921GspanPlusPotsOverlapped {
              position 30;
            }
            bit q9921GspanPlusPotsNonOverlapped {
              position 31;
            }
            bit q9923IsdnNonOverlapped {
              position 34;
            }
            bit q9923IsdnOverlapped {
              position 35;
            }
            bit q9925IsdnNonOverlapped {
              position 42;
            }
            bit q9925IsdnOverlapped {
              position 43;
            }
            bit q9923AnnexMPotsExtUsNonOverlapped {
              position 56;
            }
            bit q9923AnnexMPotsExtUsOverlapped {
              position 57;
            }
            bit q9925AnnexMPotsExtUsNonOverlapped {
              position 60;
            }
            bit q9925AnnexMPotsExtUsOverlapped {
              position 61;
            }
          }
          description
           "The transmission mode of the ATU-C. This object returns if there is no mode currently known. The initialization with the ATU-R will determine the mode used. REFERENCE Section 7.3.2 ITU G.997.1.";
          smiv2:max-access read-only;
          smiv2:oid 1.3.6.1.4.1.1332.1.1.5.3.36.3.1.5;
        }

        leaf msanAdslLineExtnClockType {
          type enumeration {
            enum oscillator {
              value 0;
            }
            enum crystal {
              value 4;
            }
          }
          description
           "This object indicates parameter to set use of either crystal or oscillator.";
          smiv2:max-access read-only;
          smiv2:oid 1.3.6.1.4.1.1332.1.1.5.3.36.3.1.6;
        }

        leaf msanAdslLineExtnLineDmtTrellis {
          type enumeration {
            enum trellisOn {
              value 1;
            }
            enum trellisOff {
              value 2;
            }
          }
          description
           "Parameter that indicates whether trellis coding has been enabled or disabled. Trellis coding should always be enabled for its clear performance advantage.";
          smiv2:max-access read-only;
          smiv2:oid 1.3.6.1.4.1.1332.1.1.5.3.36.3.1.7;
        }

        leaf msanAdslLineExtnTransAturCap {
          type bits {
            bit ansit1413 {
              position 0;
            }
            bit etsi {
              position 1;
            }
            bit q9921PotsNonOverlapped {
              position 2;
            }
            bit q9921PotsOverlapped {
              position 3;
            }
            bit q9921IsdnNonOverlapped {
              position 4;
            }
            bit q9921isdnOverlapped {
              position 5;
            }
            bit q9921tcmIsdnNonOverlapped {
              position 6;
            }
            bit q9921tcmIsdnOverlapped {
              position 7;
            }
            bit q9922potsNonOverlapeed {
              position 8;
            }
            bit q9922potsOverlapped {
              position 9;
            }
            bit q9922tcmIsdnNonOverlapped {
              position 10;
            }
            bit q9922tcmIsdnOverlapped {
              position 11;
            }
            bit q9921tcmIsdnSymmetric {
              position 12;
            }
            bit adslPlusPotsNonOverlapped {
              position 13;
            }
            bit adslPlusPotsOverlapped {
              position 18;
            }
            bit q9921GspanPlusPlusPotsNonOverlapped {
              position 20;
            }
            bit q9921GspanPlusPlusPotsOverlapped {
              position 21;
            }
            bit q9923Readsl2PotsOverlapped {
              position 22;
            }
            bit q9923Readsl2PotsNonOverlapped {
              position 23;
            }
            bit vdslOverlapped {
              position 24;
            }
            bit vdslNonOverlapped {
              position 25;
            }
            bit q9925Adsl2PlusPotsNonOverlapped {
              position 26;
            }
            bit q9925Adsl2PlusPotsOverlapped {
              position 27;
            }
            bit q9923Adsl2PotsNonOverlapped {
              position 28;
            }
            bit q9923Adsl2PotsOverlapped {
              position 29;
            }
            bit q9921GspanPlusPotsOverlapped {
              position 30;
            }
            bit q9921GspanPlusPotsNonOverlapped {
              position 31;
            }
            bit q9923IsdnNonOverlapped {
              position 34;
            }
            bit q9923IsdnOverlapped {
              position 35;
            }
            bit q9925IsdnNonOverlapped {
              position 42;
            }
            bit q9925IsdnOverlapped {
              position 43;
            }
            bit q9923AnnexMPotsExtUsNonOverlapped {
              position 56;
            }
            bit q9923AnnexMPotsExtUsOverlapped {
              position 57;
            }
            bit q9925AnnexMPotsExtUsNonOverlapped {
              position 60;
            }
            bit q9925AnnexMPotsExtUsOverlapped {
              position 61;
            }
          }
          description
           "The transmission modes that the ATU-R is capable of supporting. The modes available are limited by the design of the equipment.";
          smiv2:max-access read-only;
          smiv2:oid 1.3.6.1.4.1.1332.1.1.5.3.36.3.1.8;
        }

        leaf msanAdslLineExtnPMConfPMSF {
          type enumeration {
            enum l3ToL0StateForce {
              value 0;
            }
            enum l0ToL2StateForce {
              value 2;
            }
            enum l3StateForce {
              value 3;
            }
            enum l2ToL0StateForce {
              value 4;
            }
          }
          description
           "PM-related parameter used by the ATU-C to force a change in the line state.(Not available for ADSL/ADSL2Plus).";
          smiv2:max-access read-write;
          smiv2:oid 1.3.6.1.4.1.1332.1.1.5.3.36.3.1.9;
        }

        leaf msanAdslLineExtnDeltConfLDSF {
          type enumeration {
            enum inhibit {
              value 0;
            }
            enum force {
              value 1;
            }
          }
          description
           "DELT-related parameter used by the ATU-C to force the line into loop diagnostics mode.(Not available for ADSL and ADSL2plus).";
          smiv2:max-access read-write;
          smiv2:oid 1.3.6.1.4.1.1332.1.1.5.3.36.3.1.10;
        }

        leaf msanAdslLineExtnTransAtucConfig {
          type bits {
            bit ansit1413 {
              position 0;
            }
            bit etsi {
              position 1;
            }
            bit q9921PotsNonOverlapped {
              position 2;
            }
            bit q9921PotsOverlapped {
              position 3;
            }
            bit q9921IsdnNonOverlapped {
              position 4;
            }
            bit q9921isdnOverlapped {
              position 5;
            }
            bit q9921tcmIsdnNonOverlapped {
              position 6;
            }
            bit q9921tcmIsdnOverlapped {
              position 7;
            }
            bit q9922potsNonOverlapeed {
              position 8;
            }
            bit q9922potsOverlapped {
              position 9;
            }
            bit q9922tcmIsdnNonOverlapped {
              position 10;
            }
            bit q9922tcmIsdnOverlapped {
              position 11;
            }
            bit q9921tcmIsdnSymmetric {
              position 12;
            }
            bit adslPlusPotsNonOverlapped {
              position 13;
            }
            bit adslPlusPotsOverlapped {
              position 18;
            }
            bit q9921GspanPlusPlusPotsNonOverlapped {
              position 20;
            }
            bit q9921GspanPlusPlusPotsOverlapped {
              position 21;
            }
            bit q9923Readsl2PotsOverlapped {
              position 22;
            }
            bit q9923Readsl2PotsNonOverlapped {
              position 23;
            }
            bit q9925Adsl2PlusPotsNonOverlapped {
              position 26;
            }
            bit q9925Adsl2PlusPotsOverlapped {
              position 27;
            }
            bit q9923Adsl2PotsNonOverlapped {
              position 28;
            }
            bit q9923Adsl2PotsOverlapped {
              position 29;
            }
            bit q9921GspanPlusPotsOverlapped {
              position 30;
            }
            bit q9921GspanPlusPotsNonOverlapped {
              position 31;
            }
            bit q9923IsdnNonOverlapped {
              position 34;
            }
            bit q9923IsdnOverlapped {
              position 35;
            }
            bit q9925IsdnNonOverlapped {
              position 42;
            }
            bit q9925IsdnOverlapped {
              position 43;
            }
            bit q9923AnnexMPotsExtUsNonOverlapped {
              position 56;
            }
            bit q9923AnnexMPotsExtUsOverlapped {
              position 57;
            }
            bit q9925AnnexMPotsExtUsNonOverlapped {
              position 60;
            }
            bit q9925AnnexMPotsExtUsOverlapped {
              position 61;
            }
          }
          description
           "The transmission modes that the ATU-C is capable of supporting. The modes available are limited by the design of the equipment. REFERENCE Section 7.3.2 ITU G.997.1.";
          smiv2:max-access read-write;
          smiv2:oid 1.3.6.1.4.1.1332.1.1.5.3.36.3.1.11;
        }

        leaf msanAdslLineExtnAtucCurrOutputPwr {
          type int32;
          description
           "This parameter indicates the measure of total output power transmitted by this ATU. The value of this parameter is dynamic and will also show the change in Tx power due to Power Management. For example, the value will decrease in L2 low power mode. This value can be negative";
          smiv2:max-access read-only;
          smiv2:oid 1.3.6.1.4.1.1332.1.1.5.3.36.3.1.12;
        }

        leaf msanAdslLineExtnAtucBinSNRMargin {
          type binary {
            length "0..64";
          }
          description
           "This Conexant parameter is an array of upstream SNR Margin values in dB. Each array entry represents the SNR Margin value for particular sub carrier.";
          smiv2:max-access read-only;
          smiv2:oid 1.3.6.1.4.1.1332.1.1.5.3.36.3.1.13;
        }

        leaf msanAdslLineExtnUtopiaL2RxAddrSecond {
          type int32 {
            range "0..254";
          }
          description
           "Conexant parameter to set UTOPIA Level 2 Rx address for the secondary bearer channel in case of Dual Latency.";
          smiv2:max-access read-only;
          smiv2:oid 1.3.6.1.4.1.1332.1.1.5.3.36.3.1.14;
        }

        leaf msanAdslLineExtnUtopiaL2TxAddrSecond {
          type int32 {
            range "0..254";
          }
          description
           "Conexant parameter to set UTOPIA Level 2 Tx address for the secondary bearer channel in case of Dual Latency.";
          smiv2:max-access read-only;
          smiv2:oid 1.3.6.1.4.1.1332.1.1.5.3.36.3.1.15;
        }

        leaf msanAdslLineExtnDsBinSnrUpdate {
          type enumeration {
            enum disable {
              value 0;
            }
            enum enable {
              value 1;
            }
          }
          description
           "Conexant parameter to enable or disable collection of downstream SNR bin status";
          smiv2:max-access read-write;
          smiv2:oid 1.3.6.1.4.1.1332.1.1.5.3.36.3.1.16;
        }

        leaf msanAdslLineExtnServiceType {
          type enumeration {
            enum multimode {
              value 1;
            }
            enum reserved {
              value 2;
            }
            enum t1413 {
              value 3;
            }
            enum gDmt {
              value 4;
            }
            enum adsl2plus {
              value 6;
            }
            enum adsl2 {
              value 7;
            }
            enum adsl2plusAutoAnnexM {
              value 8;
            }
            enum adsl2AutoAnnexM {
              value 9;
            }
            enum reAdsl2 {
              value 10;
            }
          }
          description
           "The service type configured in ADSL configuration profile which applies for this line.
            Supported values:
            1:  multimode
            2:  reserved
            3:  T1_413
            4:  G.DMT
            6:  ADSL2+
            7:  ADSL2
            8:  ADSL2+ AUTO[+Annex M]
            9:  ADSL2 AUTO[+Annex M]
            10: READSL2";
          smiv2:max-access read-only;
          smiv2:oid 1.3.6.1.4.1.1332.1.1.5.3.36.3.1.17;
        }
      }
    }

    container msanAdslAturPhysExtnTable {
      description
       "This table is an extention to adslAtucPhysTable defined in rfc-2662. This table provides one row for each ATUR. Each row contains the Physical Layer Parameters table for that ATUR.";
      smiv2:oid 1.3.6.1.4.1.1332.1.1.5.3.36.4;

      list msanAdslAturPhysExtnEntry {
        key ifIndex;
        description
         "An entry (conceptual row) in the msanAdslAturPhysExtnTable.
          The Table is indexed by ifIndex.";
        smiv2:oid 1.3.6.1.4.1.1332.1.1.5.3.36.4.1;

        leaf ifIndex {
          type leafref {
            path "/if-mib:interfaces/if-mib:ifEntry/if-mib:ifIndex";
          }
        }

        leaf msanAdslAturPhysExtnConfig {
          type binary {
            length "0..30";
          }
          description
           "This object provides the upstream and downstream ATU-R configuration data, as defined in T1.413 i2, Sections 6.4, 6.6, 7.4, 7.6 and Table 27.";
          smiv2:max-access read-only;
          smiv2:oid 1.3.6.1.4.1.1332.1.1.5.3.36.4.1.1;
        }

        leaf msanAdslAturPhysExtnChanPerfCD {
          type int32;
          description
           "The far-end delineated total cell count performance parameter is a count of the total number of cells passed through the cell delineation and HEC function process operating on the ATM Data Path while in the SYNC state.(Not available for ADSL).";
          smiv2:max-access read-only;
          smiv2:oid 1.3.6.1.4.1.1332.1.1.5.3.36.4.1.2;
        }

        leaf msanAdslAturPhysExtnChanPerfCU {
          type int32;
          description
           "The far-end user total cell count performance parameter is a count of the total number of cells in the ATM Data Path delivered at the V-C (for ATU-C) or T-R (for ATUR) interface. (Not available for ADSL).";
          smiv2:max-access read-only;
          smiv2:oid 1.3.6.1.4.1.1332.1.1.5.3.36.4.1.3;
        }

        leaf msanAdslAturPhysExtnChanPerfBE {
          type int32;
          description
           "The far-end idle bit error count performance parameter is a count of the number of bit errors in the idle cell payload received in the ATM Data Path at the far-end. (Not available for ADSL).";
          smiv2:max-access read-only;
          smiv2:oid 1.3.6.1.4.1.1332.1.1.5.3.36.4.1.4;
        }

        leaf msanAdslAturPhysExtnDeltHLINSCds {
          type int32;
          description
           "DELT-related parameter that provides the scale factor to be applied to the downstream Hlin(f) values.(Not available for ADSL and ADSL2plus).";
          smiv2:max-access read-only;
          smiv2:oid 1.3.6.1.4.1.1332.1.1.5.3.36.4.1.5;
        }

        leaf msanAdslAturPhysExtnDeltHLINpsds {
          type binary {
            length "0..2048";
          }
          description
           "DELT-related parameter that provides an array of complex downstream Hlin(f) values in linear scale. (Not available for ADSL and ADSL2plus). Every two octets refer to one element in this array of octets.";
          smiv2:max-access read-only;
          smiv2:oid 1.3.6.1.4.1.1332.1.1.5.3.36.4.1.6;
        }

        leaf msanAdslAturPhysExtnDeltHLOGMTds {
          type int32;
          description
           "DELT-related parameter that provides the number of symbols used to measure the downstream Hlog(f). (Not available for ADSL and ADSL2plus).";
          smiv2:max-access read-only;
          smiv2:oid 1.3.6.1.4.1.1332.1.1.5.3.36.4.1.7;
        }

        leaf msanAdslAturPhysExtnDeltHLOGpsus {
          type binary {
            length "0..1024";
          }
          description
           "DELT-related parameter that provides an array of real downstream Hlog(f) values in dB. (Not available for ADSL and ADSL2plus).";
          smiv2:max-access read-only;
          smiv2:oid 1.3.6.1.4.1.1332.1.1.5.3.36.4.1.8;
        }

        leaf msanAdslAturPhysExtnDeltQLNMTds {
          type int32;
          description
           "DELT-related parameter that provides the number of symbols used to measure the downstream QLN(f) values. (Not available for ADSL and ADSL2plus).";
          smiv2:max-access read-only;
          smiv2:oid 1.3.6.1.4.1.1332.1.1.5.3.36.4.1.9;
        }

        leaf msanAdslAturPhysExtnDeltQLNpsds {
          type binary {
            length "0..512";
          }
          description
           "DELT-related parameter that provides an array of real downstream QLN(f) values in dB. (Not available for ADSL and ADSL2plus). Every two octets refer to one element in this array of octets.";
          smiv2:max-access read-only;
          smiv2:oid 1.3.6.1.4.1.1332.1.1.5.3.36.4.1.10;
        }

        leaf msanAdslAturPhysExtnDeltLastTxState {
          type enumeration {
            enum dmtaturg9941 {
              value 0;
            }
            enum dmtaturquiet1 {
              value 1;
            }
            enum dmtaturcomb1 {
              value 2;
            }
            enum dmtaturquiet2 {
              value 3;
            }
            enum dmtaturcomb2 {
              value 4;
            }
            enum dmtaturicomb1 {
              value 5;
            }
            enum dmtaturlineprob {
              value 6;
            }
            enum dmtaturquiet3 {
              value 7;
            }
            enum dmtaturcomb3 {
              value 8;
            }
            enum dmtaturicomb2 {
              value 9;
            }
            enum dmtaturmsgfmt {
              value 10;
            }
            enum dmtaturmsgpcb {
              value 11;
            }
            enum dmtaturreverb1 {
              value 12;
            }
            enum dmtaturquiet4 {
              value 13;
            }
            enum dmtaturreverb2 {
              value 14;
            }
            enum dmtaturquiet5 {
              value 15;
            }
            enum dmtaturreverb3 {
              value 16;
            }
            enum dmtaturect {
              value 17;
            }
            enum dmtaturreverb4 {
              value 18;
            }
            enum dmtatursegue1 {
              value 19;
            }
            enum dmtaturreverb5 {
              value 20;
            }
            enum dmtatursegue2 {
              value 21;
            }
            enum dmtaturmsg1 {
              value 22;
            }
            enum dmtaturmedley {
              value 23;
            }
            enum dmtaturexchmarker {
              value 24;
            }
            enum dmtaturmsg2 {
              value 25;
            }
            enum dmtaturreverb6 {
              value 26;
            }
            enum dmtatursegue3 {
              value 27;
            }
            enum dmtaturparams {
              value 28;
            }
            enum dmtaturreverb7 {
              value 29;
            }
            enum dmtatursegue4 {
              value 30;
            }
            enum dmtaturshowtime {
              value 31;
            }
          }
          description
           "DELT-related parameter that provides last successful transmitted initialization state by the ATU-R. (Not available for ADSL and ADSL2plus).";
          smiv2:max-access read-only;
          smiv2:oid 1.3.6.1.4.1.1332.1.1.5.3.36.4.1.11;
        }

        leaf msanAdslAturMSGus {
          type yang:gauge32;
          description
           "Indicates the Overhead Channel.  This feature is not supported by DSLPHY as yet.";
          smiv2:max-access read-only;
          smiv2:oid 1.3.6.1.4.1.1332.1.1.5.3.36.4.1.12;
        }

        leaf msanAdslAturDeltSNRMTds {
          type yang:gauge32;
          description
           "DELT-related parameter that provides the number of symbols used to measure the downstream SNR(f) values. (Not available for ADSL and ADSL2plus)";
          smiv2:max-access read-only;
          smiv2:oid 1.3.6.1.4.1.1332.1.1.5.3.36.4.1.13;
        }

        leaf msanAdslAturSATN {
          type int32;
          description
           "DELT-related parameter that provides the downtream signal attenuation (length = 4 bytes). (Not available for ADSL and ADSL2plus). For further details, Refer to Section 7.5.1.9 Revised Recommendation G.997.1.";
          smiv2:max-access read-only;
          smiv2:oid 1.3.6.1.4.1.1332.1.1.5.3.36.4.1.14;
        }

        leaf msanAdslAturPhysExtnSystemVendorId {
          type binary {
            length "0..9";
          }
          description
           "Indicates the Vendor ID as inserted by the ATU-R in the Embedded Operations Channel(ADSL). Typically identiies the ATU-R system integrator which usually refers to the vendor of the smallest field-replaceable unit. ATU-R System Vendor ID may not be the same as ATU-R G.994.1 Vendor ID. For ADSL2, provides the Vendor ID as inserted by the ATU-R in the Overhead Messages. It is not available for ADSL. This is string of 8 octets containing 2 octet country code , 4 octet vendor id and 2 octet vendor revision number.";
          smiv2:max-access read-only;
          smiv2:oid 1.3.6.1.4.1.1332.1.1.5.3.36.4.1.15;
        }

        leaf msanAdslAturPhysExtnGainspsDs {
          type binary {
            length "0..1024";
          }
          description
           "This parameter defines the downstream gains allocation table per bin. For further details, Refer to Section 7.5.1.21.3 Revised Recommendation G.997.1. It is supported for ADSL2/ADSl2plus only.";
          smiv2:max-access read-only;
          smiv2:oid 1.3.6.1.4.1.1332.1.1.5.3.36.4.1.16;
        }

        leaf msanAdslAturPhysExtnSelfTestResult {
          type yang:gauge32;
          description
           "Defines the ATU-R selftest result. The most significant octet is: 00 hex if the self-test passed or 01 hex if the self-test failed. Interpretation of the other octets is vendor discretionary and can be interpreted in combination with G.994.1 and system Vendor IDs. For further details, refer to Section 7.4.10 Revised Recommendation G.997.1.";
          smiv2:max-access read-only;
          smiv2:oid 1.3.6.1.4.1.1332.1.1.5.3.36.4.1.17;
        }

        leaf msanAdslAturPhysExtnG9941VendorId {
          type binary {
            length "0..9";
          }
          description
           "Indicates the Vendor ID as inserted by the ATU-R in the G.994.1 CLR message.The G.994.1 Vendor ID typically identifies the vendor of the ATU-R G.994.1 functionality. This is string of 8 octets containing 2 octet country code , 4 octet vendor id and 2 octet vendor revision number. For further details, refer to Section 7.4.2 Revised Recommendation G.997.1.";
          smiv2:max-access read-only;
          smiv2:oid 1.3.6.1.4.1.1332.1.1.5.3.36.4.1.18;
        }

        leaf msanAdslAturPhysExtnTsspsDs {
          type binary {
            length "0..128";
          }
          description
           "This parameter provides the Downstream Transmit Spectrum Shaping parameter expressed as the set of break points exchanged during G994.1. Value of this parameter is in range 0 - 127, in multiples of -0.5 dB. 127 is a special value indicating the subcarrier is not transmitted. It is available only for ADSL2/ADSL2plus. For further details, Refer to Section 7.5.1.21.5 Revised Recommendation G.997.1";
          smiv2:max-access read-only;
          smiv2:oid 1.3.6.1.4.1.1332.1.1.5.3.36.4.1.19;
        }

        leaf msanAdslAturPhysExtnActPsdDs {
          type int32;
          description
           "This parameter defines the average downstream transmit power spectrum density over the used subcarriers delivered by the ATU-C at the U-C reference point, at the instant of measurement. It's value ranges from -90 to 0, in 0.1 dB/Hz steps. It is available only for ADSL2/ADSL2plus.For further details, Refer to Section 7.5.1.14 Revised Recommendation G.997.1.";
          smiv2:max-access read-only;
          smiv2:oid 1.3.6.1.4.1.1332.1.1.5.3.36.4.1.20;
        }

        leaf msanAdslAturPhysExtnBitSwapCount {
          type uint32;
          description
           "This Conexant parameter indicates the bit swap count. It can read only in data mode";
          smiv2:max-access read-only;
          smiv2:oid 1.3.6.1.4.1.1332.1.1.5.3.36.4.1.21;
        }

        leaf msanAdslAturPhysExtnPsdMaskMode {
          type enumeration {
            enum coMsk2 {
              value 0;
            }
            enum flatMsk {
              value 3;
            }
            enum cabMsk2 {
              value 4;
            }
            enum adsl2NonovlpFlat {
              value 259;
            }
            enum adsl2NonovlpM1 {
              value 275;
            }
            enum adsl2NonovlpM2 {
              value 291;
            }
            enum coMsk2Rfi {
              value 32768;
            }
            enum flatMskRfi {
              value 32771;
            }
            enum cabMsk2Rfi {
              value 32772;
            }
            enum coMsk2Rfi0 {
              value 49152;
            }
          }
          description
           "This conexant parameter that indicates the actual PSD Mask currently being used by ATU-R";
          smiv2:max-access read-only;
          smiv2:oid 1.3.6.1.4.1.1332.1.1.5.3.36.4.1.22;
        }
      }
    }

    container msanEapsDomainTable {
      description
       "EAPS domain configuration.";
      smiv2:oid 1.3.6.1.4.1.1332.1.1.5.3.37.2;

      list msanEapsDomainEntry {
        key msanEapsDomainName;
        description
         "Description.";
        smiv2:oid 1.3.6.1.4.1.1332.1.1.5.3.37.2.1;

        leaf msanEapsDomainName {
          type binary {
            length "1..12";
          }
          description
           "Description of the EAPS domain. Each msanEapsDomainName value in this
            table must be unique.";
          smiv2:max-access not-accessible;
          smiv2:oid 1.3.6.1.4.1.1332.1.1.5.3.37.2.1.2;
        }

        leaf msanEapsDomainDeviceRole {
          type enumeration {
            enum master {
              value 1;
            }
            enum transit {
              value 2;
            }
          }
          description
           "Role of the node in the EAPS domain (Master or Transit)";
          smiv2:defval transit;
          smiv2:max-access read-write;
          smiv2:oid 1.3.6.1.4.1.1332.1.1.5.3.37.2.1.3;
        }

        leaf msanEapsDomainHelloTime {
          type int32 {
            range "1..15";
          }
          description
           "EAPS domain hello frame send interval.
            This value must be lower than msanEapsDomainFailTimeout";
          smiv2:defval 1;
          smiv2:max-access read-write;
          smiv2:oid 1.3.6.1.4.1.1332.1.1.5.3.37.2.1.4;
        }

        leaf msanEapsDomainFailTimeout {
          type int32 {
            range "2..300";
          }
          description
           "EAPS fail timeout.
            This value must be higher than msanEapsDomainHelloTime";
          smiv2:defval 3;
          smiv2:max-access read-write;
          smiv2:oid 1.3.6.1.4.1.1332.1.1.5.3.37.2.1.5;
        }

        leaf msanEapsDomainAdminState {
          type enumeration {
            enum enable {
              value 1;
            }
            enum disable {
              value 2;
            }
          }
          description
           "EAPS domain administrative state.
            State can be changed from disable to enable only when all parameters
            in this table are defined.";
          smiv2:defval disable;
          smiv2:max-access read-write;
          smiv2:oid 1.3.6.1.4.1.1332.1.1.5.3.37.2.1.6;
        }

        leaf msanEapsDomainPrimaryIfIndex {
          type int32;
          description
           "EAPS primary interface. The value must be different from msanEapsSecondaryIfIndex.
            
            The interface identified by a particular value of this index is the same
            interface as identified by the same value of ifIndex.
            ifType of selected interface can be ethernetCsmacd(6) or ieee8023adLag (161).
            
            This parameter can be undefined when EAPS domain is created and msanEapsDomainAdminState
            is disable.";
          smiv2:max-access read-write;
          smiv2:oid 1.3.6.1.4.1.1332.1.1.5.3.37.2.1.7;
        }

        leaf msanEapsDomainSecondaryIfIndex {
          type int32;
          description
           "EAPS secondary interface. The value must be different from msanEapsPrimaryIfIndex.
            
            The interface identified by a particular value of this index is the same
            interface as identified by the same value of ifIndex.
            ifType of selected interface can be ethernetCsmacd(6) or ieee8023adLag (161).
            
            This parameter can be undefined when EAPS domain is created and msanEapsDomainAdminState
            is disable.";
          smiv2:max-access read-write;
          smiv2:oid 1.3.6.1.4.1.1332.1.1.5.3.37.2.1.8;
        }

        leaf msanEapsDomainCntrlVlanId {
          type int32;
          description
           "EAPS control VLAN ID.
            Selected VLAN ID must exists in dot1qVlanStaticTable.
            
            This parameter can be undefined when EAPS domain is created and msanEapsDomainAdminState
            is disable.";
          smiv2:max-access read-write;
          smiv2:oid 1.3.6.1.4.1.1332.1.1.5.3.37.2.1.9;
        }

        leaf msanEapsDomainRowStatus {
          type snmpv2-tc:RowStatus;
          description
           "The row status object controls the creation/deletion of rows in this table.
            For row creation use createAndWait(5) [createAndGo(4) is not supported].
            
            If msanEapsDomainAdminState is disable, created row can be actived by row status object
            also when next parameters are not defined:
            - msanEapsDomainPrimaryifIndex
            - msanEapsDomainSecondaryifIndex
            - msanEapsDomainCntrlVlanId";
          smiv2:max-access read-write;
          smiv2:oid 1.3.6.1.4.1.1332.1.1.5.3.37.2.1.10;
        }
      }
    }

    container msanEapsDomainProtVlanTable {
      description
       "List of protected VLANs for EAPS domain.";
      smiv2:oid 1.3.6.1.4.1.1332.1.1.5.3.37.3;

      list msanEapsDomainProtVlanEntry {
        key "msanEapsDomainName dot1qVlanIndex";
        description
         "Description.";
        smiv2:oid 1.3.6.1.4.1.1332.1.1.5.3.37.3.1;

        leaf msanEapsDomainName {
          type leafref {
            path "/iskratel-msan:ISKRATEL-MSAN-MIB/iskratel-msan:msanEapsDomainTable/iskratel-msan:msanEapsDomainEntry/iskratel-msan:msanEapsDomainName";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanEapsDomainProtVlanRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.37.3.1.1;
        }
      }
    }

    container msanCpeTypeTable {
      description
       "List of possible CPE types.";
      smiv2:oid 1.3.6.1.4.1.1332.1.1.5.3.38.2;

      list msanCpeTypeEntry {
        key msanCpeTypeName;
        description
         "Description.";
        smiv2:oid 1.3.6.1.4.1.1332.1.1.5.3.38.2.1;

        leaf msanCpeTypeName {
          type binary {
            length "0..20";
          }
          description
           "Usage name of CPE model.";
          smiv2:max-access not-accessible;
          smiv2:oid 1.3.6.1.4.1.1332.1.1.5.3.38.2.1.1;
        }

        leaf msanCpeTypePortNum {
          type int32;
          description
           "Number of CPE user ports.";
          smiv2:max-access read-write;
          smiv2:oid 1.3.6.1.4.1.1332.1.1.5.3.38.2.1.2;
        }
      }
    }

    container msanCpeIntfTypeTable {
      description
       "Tabel defines which CPE model can be connected to selected interface.";
      smiv2:oid 1.3.6.1.4.1.1332.1.1.5.3.38.3;

      list msanCpeIntfTypeEntry {
        key "ifIndex msanCpeTypeName";
        description
         "Description.";
        smiv2:oid 1.3.6.1.4.1.1332.1.1.5.3.38.3.1;

        leaf ifIndex {
          type leafref {
            path "/if-mib:interfaces/if-mib:ifEntry/if-mib:ifIndex";
          }
        }

        leaf msanCpeTypeName {
          type leafref {
            path "/iskratel-msan:ISKRATEL-MSAN-MIB/iskratel-msan:msanCpeTypeTable/iskratel-msan:msanCpeTypeEntry/iskratel-msan:msanCpeTypeName";
          }
        }

        leaf msanCpeIntfTypeRowStatus {
          type snmpv2-tc:RowStatus;
          description
           "The row status object controls the creation/deletion of rows in this table.
            Setting this object to createAndGo(4) creates a row in this table.
            Setting this object to destroy(6) will remove this entry.
            Read values: active(1).
            Other values are currently not supported.";
          smiv2:max-access read-write;
          smiv2:oid 1.3.6.1.4.1.1332.1.1.5.3.38.3.1.1;
        }

        leaf msanCpeIntfTypeHwVersion {
          type binary {
            length "0..32";
          }
          description
           "Connected CPE hardware version.";
          smiv2:max-access read-only;
          smiv2:oid 1.3.6.1.4.1.1332.1.1.5.3.38.3.1.2;
        }

        leaf msanCpeIntfTypeSwVersion {
          type binary {
            length "0..32";
          }
          description
           "Connected CPE software version.";
          smiv2:max-access read-only;
          smiv2:oid 1.3.6.1.4.1.1332.1.1.5.3.38.3.1.3;
        }
      }
    }

    container msanCpeIntfPortTable {
      description
       "Table of CPE ports parameters";
      smiv2:oid 1.3.6.1.4.1.1332.1.1.5.3.38.4;

      list msanCpeIntfPortEntry {
        key "ifIndex msanCpeIntfPortId";
        description
         "Description.";
        smiv2:oid 1.3.6.1.4.1.1332.1.1.5.3.38.4.1;

        leaf ifIndex {
          type leafref {
            path "/if-mib:interfaces/if-mib:ifEntry/if-mib:ifIndex";
          }
        }

        leaf msanCpeIntfPortId {
          type int32;
          description
           "CPE port ID (1 .. n).";
          smiv2:max-access not-accessible;
          smiv2:oid 1.3.6.1.4.1.1332.1.1.5.3.38.4.1.1;
        }

        leaf msanCpeIntfPortPowerMode {
          type enumeration {
            enum normal {
              value 0;
            }
            enum fullPowerDown {
              value 1;
            }
            enum sleep {
              value 2;
            }
          }
          description
           "Power mode of the CPE port. When port is in Sleep(2) mode,
            automatic wake-up is also activated.  ";
          smiv2:defval normal;
          smiv2:max-access read-write;
          smiv2:oid 1.3.6.1.4.1.1332.1.1.5.3.38.4.1.2;
        }

        leaf msanCpeIntfPortLinkMode {
          type enumeration {
            enum autonegotiation {
              value 0;
            }
            enum speed100MbpsFD {
              value 1;
            }
            enum speed100MbpsHD {
              value 2;
            }
            enum speed10MbpsFD {
              value 3;
            }
            enum speed10MbpsHD {
              value 4;
            }
          }
          description
           "Speed and duplex mode of the CPE port.";
          smiv2:defval autonegotiation;
          smiv2:max-access read-write;
          smiv2:oid 1.3.6.1.4.1.1332.1.1.5.3.38.4.1.3;
        }

        leaf msanCpeIntfPortPvid {
          type int32 {
            range "1..4094";
          }
          description
           "Default Vlan ID (pVID) for selected CPE port.";
          smiv2:defval 1;
          smiv2:max-access read-write;
          smiv2:oid 1.3.6.1.4.1.1332.1.1.5.3.38.4.1.4;
        }

        leaf msanCpeIntfPortCos {
          type int32 {
            range "0..7";
          }
          description
           "Default CoS bit settings for the CPE port.";
          smiv2:defval 0;
          smiv2:max-access read-write;
          smiv2:oid 1.3.6.1.4.1.1332.1.1.5.3.38.4.1.5;
        }

        leaf msanCpeIntfPortOverrideVid {
          type enumeration {
            enum enable {
              value 1;
            }
            enum disable {
              value 2;
            }
          }
          description
           "When enable(1)VLAN ID of received tagged frame on selected CPE port
            is overwritten with default VLAN ID (msanCpeIntfPortPvid).";
          smiv2:defval disable;
          smiv2:max-access read-write;
          smiv2:oid 1.3.6.1.4.1.1332.1.1.5.3.38.4.1.6;
        }

        leaf msanCpeIntfPortOverrideCos {
          type enumeration {
            enum enable {
              value 1;
            }
            enum disable {
              value 2;
            }
          }
          description
           "When enable(1)CoS value of received tagged frame on selected CPE port
            is overwritten with default CoS bit settings (msanCpeIntfPortCos).";
          smiv2:defval disable;
          smiv2:max-access read-write;
          smiv2:oid 1.3.6.1.4.1.1332.1.1.5.3.38.4.1.7;
        }

        leaf msanCpeIntfPortProtection {
          type enumeration {
            enum unprotected {
              value 0;
            }
            enum protected {
              value 1;
            }
          }
          description
           "If protection flag is set to protected (1), other profile values cannot be edited.
            
            Protection flag is always  protected (1) and it can't be changed if  profile is assigned as dynamic:
            msanAclProfileStatus = dynamic(2)";
          smiv2:defval unprotected;
          smiv2:max-access read-write;
          smiv2:oid 1.3.6.1.4.1.1332.1.1.5.3.38.4.1.8;
        }

        leaf msanCpeIntfPortStatus {
          type enumeration {
            enum static {
              value 1;
            }
            enum dynamic {
              value 2;
            }
          }
          description
           "Profile status.
            If status is dynamic, profile values can't be edited.";
          smiv2:max-access read-only;
          smiv2:oid 1.3.6.1.4.1.1332.1.1.5.3.38.4.1.9;
        }
      }
    }

    container msanCpeTrafficTable {
      description
       "Description.";
      smiv2:oid 1.3.6.1.4.1.1332.1.1.5.3.38.5;

      list msanCpeTrafficEntry {
        key msanCpeTrafficId;
        description
         "Description.";
        smiv2:oid 1.3.6.1.4.1.1332.1.1.5.3.38.5.1;

        leaf msanCpeTrafficId {
          type int32;
          description
           "Number identifying traffic configuration (1 .. n).";
          smiv2:max-access not-accessible;
          smiv2:oid 1.3.6.1.4.1.1332.1.1.5.3.38.5.1.1;
        }

        leaf msanCpeTrafficName {
          type binary {
            length "0..40";
          }
          description
           "Name identifying traffic configuration. Must be unique value.";
          smiv2:max-access read-write;
          smiv2:oid 1.3.6.1.4.1.1332.1.1.5.3.38.5.1.2;
        }

        leaf msanCpeTrafficSpeed {
          type int32 {
            range "0..100000";
          }
          units kbit/s;
          description
           "Maximum bitrate of services using this traffic configuration.
            Domain value is 0-100000kbit/s, where:
            - for speeds below 1Mbit/s step is 64kbit/s
            - for speeds above 1Mbit/s step is 1000kbit/s";
          smiv2:max-access read-write;
          smiv2:oid 1.3.6.1.4.1.1332.1.1.5.3.38.5.1.3;
        }

        leaf msanCpeTrafficFlowCntrlMode {
          type enumeration {
            enum enable {
              value 1;
            }
            enum disable {
              value 2;
            }
          }
          description
           "Flow control mode. When enable(1) and speed is to be exceeded, device will send
            PAUSE flow control packet. If disable(2) packet will be just dropped.";
          smiv2:defval disable;
          smiv2:max-access read-write;
          smiv2:oid 1.3.6.1.4.1.1332.1.1.5.3.38.5.1.4;
        }

        leaf msanCpeTrafficRowStatus {
          type snmpv2-tc:RowStatus;
          description
           "The row status object controls the creation/deletion of rows in this table.
            For row creation use createAndWait(5) [createAndGo(4) is not supported].
            Setting this object to active(1) will activate this entry, if msanCpeTrafficName is defined.
            Setting this object to destroy(6) will remove this entry.";
          smiv2:max-access read-write;
          smiv2:oid 1.3.6.1.4.1.1332.1.1.5.3.38.5.1.5;
        }

        leaf msanCpeTrafficProtection {
          type enumeration {
            enum unprotected {
              value 0;
            }
            enum protected {
              value 1;
            }
          }
          description
           "If protection flag is set to protected (1), other profile values cannot be edited.
            
            Protection flag is always  protected (1) and it can't be changed if  profile is assigned as dynamic:
            msanAclProfileStatus = dynamic(2)";
          smiv2:defval unprotected;
          smiv2:max-access read-write;
          smiv2:oid 1.3.6.1.4.1.1332.1.1.5.3.38.5.1.6;
        }

        leaf msanCpeTrafficStatus {
          type enumeration {
            enum static {
              value 1;
            }
            enum dynamic {
              value 2;
            }
          }
          description
           "Profile status.
            If status is dynamic, profile values can't be edited.";
          smiv2:max-access read-only;
          smiv2:oid 1.3.6.1.4.1.1332.1.1.5.3.38.5.1.7;
        }
      }
    }

    container msanCpeServiceTable {
      description
       "Description.";
      smiv2:oid 1.3.6.1.4.1.1332.1.1.5.3.38.6;

      list msanCpeServiceEntry {
        key msanCpeServiceId;
        description
         "Description.";
        smiv2:oid 1.3.6.1.4.1.1332.1.1.5.3.38.6.1;

        leaf msanCpeServiceId {
          type int32;
          description
           "Number identifying service configuration (0 .. n).";
          smiv2:max-access not-accessible;
          smiv2:oid 1.3.6.1.4.1.1332.1.1.5.3.38.6.1.1;
        }

        leaf msanCpeServiceName {
          type binary {
            length "0..40";
          }
          description
           "Name identifying service. Must be unique value.";
          smiv2:max-access read-write;
          smiv2:oid 1.3.6.1.4.1.1332.1.1.5.3.38.6.1.2;
        }

        leaf msanCpeServiceCVlanId {
          type int32 {
            range "1..4094";
          }
          description
           "Customer VLAN ID, used for all frames belong to this service.";
          smiv2:defval 1;
          smiv2:max-access read-write;
          smiv2:oid 1.3.6.1.4.1.1332.1.1.5.3.38.6.1.3;
        }

        leaf msanCpeServiceCCos {
          type int32 {
            range "0..7";
          }
          description
           "CoS bit settings for all frames belonging to this service.";
          smiv2:defval 0;
          smiv2:max-access read-write;
          smiv2:oid 1.3.6.1.4.1.1332.1.1.5.3.38.6.1.4;
        }

        leaf msanCpeServiceTrafficId {
          type int32;
          description
           "Reference to parameter msanCpeTrafficId (1 .. n), which identifies traffic configuration .
            Value 0 is used when traffic configuration is not defined.";
          smiv2:defval 0;
          smiv2:max-access read-write;
          smiv2:oid 1.3.6.1.4.1.1332.1.1.5.3.38.6.1.5;
        }

        leaf msanCpeServiceUntaggedPorts {
          type binary {
            length "0..2";
          }
          description
           "The set of ports (bitmask) which should transmit egress packets as untagged.
            When untagged frame is received on this ports set, appropriate default VLAN ID
            (msanCpeIntfPortPvid) and default CoS bits (msanCpeIntfPortCos) are set.";
          smiv2:defval "'00'H";
          smiv2:max-access read-write;
          smiv2:oid 1.3.6.1.4.1.1332.1.1.5.3.38.6.1.6;
        }

        leaf msanCpeServiceTaggedPorts {
          type binary {
            length "0..2";
          }
          description
           "The set of ports (bitmask) where frames can be received only if they have
            appropriate Customer VLAN ID (msanCpeServiceCVlanId). Otherwise they are dropped.
            When transmitting frames to this set of ports, VLAN tags are not removed.
             ";
          smiv2:defval "'00'H";
          smiv2:max-access read-write;
          smiv2:oid 1.3.6.1.4.1.1332.1.1.5.3.38.6.1.7;
        }

        leaf msanCpeServiceCMltcstMode {
          type enumeration {
            enum disableIGMPprocessing {
              value 0;
            }
            enum igmpV2SnoopNormalLeave {
              value 1;
            }
            enum igmpV2SnoopFastLeave {
              value 2;
            }
          }
          description
           "Mode of multicast operation for this service.";
          smiv2:defval disableIGMPprocessing;
          smiv2:max-access read-write;
          smiv2:oid 1.3.6.1.4.1.1332.1.1.5.3.38.6.1.8;
        }

        leaf msanCpeServiceRowStatus {
          type snmpv2-tc:RowStatus;
          description
           "The row status object controls the creation/deletion of rows in this table.
            For row creation use createAndWait(5) [createAndGo(4) is not supported].
            Setting this object to active(1) will activate this entry, if msanCpeServiceName
            and msanCpeServiceTrafficId are defined.
            Setting this object to destroy(6) will remove this entry.";
          smiv2:max-access read-write;
          smiv2:oid 1.3.6.1.4.1.1332.1.1.5.3.38.6.1.9;
        }

        leaf msanCpeServiceTypeName {
          type binary {
            length "0..20";
          }
          description
           "Usage name of CPE model.
            Must be one of predefined msanCpeTypeName values.";
          smiv2:max-access read-write;
          smiv2:oid 1.3.6.1.4.1.1332.1.1.5.3.38.6.1.10;
        }

        leaf msanCpeServiceProtection {
          type enumeration {
            enum unprotected {
              value 0;
            }
            enum protected {
              value 1;
            }
          }
          description
           "If protection flag is set to protected (1), other profile values cannot be edited.
            
            Protection flag is always  protected (1) and it can't be changed if  profile is assigned as dynamic:
            msanAclProfileStatus = dynamic(2)";
          smiv2:defval unprotected;
          smiv2:max-access read-write;
          smiv2:oid 1.3.6.1.4.1.1332.1.1.5.3.38.6.1.11;
        }

        leaf msanCpeServiceStatus {
          type enumeration {
            enum static {
              value 1;
            }
            enum dynamic {
              value 2;
            }
          }
          description
           "Profile status.
            If status is dynamic, profile values can't be edited.";
          smiv2:max-access read-only;
          smiv2:oid 1.3.6.1.4.1.1332.1.1.5.3.38.6.1.12;
        }
      }
    }

    container msanCpeIntfServiceTable {
      description
       "This table links CPE ports on selected interface with appropriate service.";
      smiv2:oid 1.3.6.1.4.1.1332.1.1.5.3.38.7;

      list msanCpeIntfServiceEntry {
        key "ifIndex msanCpeServiceId";
        description
         "Description.";
        smiv2:oid 1.3.6.1.4.1.1332.1.1.5.3.38.7.1;

        leaf ifIndex {
          type leafref {
            path "/if-mib:interfaces/if-mib:ifEntry/if-mib:ifIndex";
          }
        }

        leaf msanCpeServiceId {
          type leafref {
            path "/iskratel-msan:ISKRATEL-MSAN-MIB/iskratel-msan:msanCpeServiceTable/iskratel-msan:msanCpeServiceEntry/iskratel-msan:msanCpeServiceId";
          }
        }

        leaf msanCpeIntfServiceRowStatus {
          type snmpv2-tc:RowStatus;
          description
           "The row status object controls the creation/deletion of rows in this table.
            Setting this object to createAndGo(4) creates a row in this table.
            Setting this object to destroy(6) will remove this entry.
            Read values: active(1).
            Other values are currently not supported.";
          smiv2:max-access read-write;
          smiv2:oid 1.3.6.1.4.1.1332.1.1.5.3.38.7.1.1;
        }
      }
    }

    container msanBoardConfTable {
      description
       "Description.";
      smiv2:oid 1.3.6.1.4.1.1332.1.1.5.3.39.2;

      list msanBoardConfEntry {
        key msanBoardConfNr;
        description
         "Description.";
        smiv2:oid 1.3.6.1.4.1.1332.1.1.5.3.39.2.1;

        leaf msanBoardConfNr {
          type int32 {
            range "1..1000";
          }
          description
           "Unique identification of a board.";
          smiv2:max-access not-accessible;
          smiv2:oid 1.3.6.1.4.1.1332.1.1.5.3.39.2.1.1;
        }

        leaf msanBoardConfParentNr {
          type int32 {
            range "1..1000";
          }
          description
           "Unique identification of a parent board.";
          smiv2:max-access read-write;
          smiv2:oid 1.3.6.1.4.1.1332.1.1.5.3.39.2.1.2;
        }

        leaf msanBoardConfPosition {
          type int32 {
            range "1..1000";
          }
          description
           "Position of the board on the parent board.";
          smiv2:max-access read-write;
          smiv2:oid 1.3.6.1.4.1.1332.1.1.5.3.39.2.1.3;
        }

        leaf msanBoardConfType {
          type rfc1213-mib:DisplayString;
          description
           "Type of physical board (e.g. IDC, SGO, SFA, ...). This value is automatically
            set according to msanBoardConfRequiredId.";
          smiv2:max-access read-only;
          smiv2:oid 1.3.6.1.4.1.1332.1.1.5.3.39.2.1.4;
        }

        leaf msanBoardConfRequiredId {
          type rfc1213-mib:DisplayString;
          description
           "Required identification of a board, which is one of available msanBoardListId
            values (e.g. UTA6041BA).";
          smiv2:max-access read-write;
          smiv2:oid 1.3.6.1.4.1.1332.1.1.5.3.39.2.1.5;
        }

        leaf msanBoardConfActualId {
          type rfc1213-mib:DisplayString;
          description
           "Actual identification of a board (e.g. UTA6041BA050 - last three numbers define board version).";
          smiv2:max-access read-only;
          smiv2:oid 1.3.6.1.4.1.1332.1.1.5.3.39.2.1.6;
        }

        leaf msanBoardConfSerialNr {
          type rfc1213-mib:DisplayString;
          description
           "Serial number of a board.";
          smiv2:max-access read-only;
          smiv2:oid 1.3.6.1.4.1.1332.1.1.5.3.39.2.1.7;
        }

        leaf msanBoardConfDescription {
          type rfc1213-mib:DisplayString;
          description
           "Description of the board.";
          smiv2:max-access read-write;
          smiv2:oid 1.3.6.1.4.1.1332.1.1.5.3.39.2.1.8;
        }

        leaf msanBoardConfStatus {
          type enumeration {
            enum boardPresentRunning {
              value 1;
            }
            enum boardPresentNotAccessible {
              value 2;
            }
            enum boardNotPresent {
              value 3;
            }
            enum boardPresentInitProcess {
              value 4;
            }
          }
          description
           "Physical status of configured board.";
          smiv2:max-access read-only;
          smiv2:oid 1.3.6.1.4.1.1332.1.1.5.3.39.2.1.9;
        }

        leaf msanBoardConfRowStatus {
          type snmpv2-tc:RowStatus;
          description
           "The row status object controls the creation/deletion of rows in this table.
            Its semantics are the same as those for the RowStatus textual convention specified for SNMPv2.
            For row creation use createAndWait(5).
            For row activation use active(1).
            For row deactivation use notInService(2).
            For row deletion use destroy(6) (board with management interface can not be deleted).
            
            Other values are currently not supported.
            
            For row activation next terms must be accomplished:
            - all requested values (they don't have default definition) must be set
            - msanBoardConfId is one of available msanBoardListId values ";
          smiv2:max-access read-write;
          smiv2:oid 1.3.6.1.4.1.1332.1.1.5.3.39.2.1.10;
        }

        leaf msanBoardConfSwSteerVersion {
          type rfc1213-mib:DisplayString;
          description
           "The unique steer code of installed software. ";
          smiv2:max-access read-only;
          smiv2:oid 1.3.6.1.4.1.1332.1.1.5.3.39.2.1.11;
        }

        leaf msanBoardConfSwBuildDirectory {
          type rfc1213-mib:DisplayString;
          description
           "The directory where installed software was build on. ";
          smiv2:max-access read-only;
          smiv2:oid 1.3.6.1.4.1.1332.1.1.5.3.39.2.1.12;
        }

        leaf msanBoardConfSwBuildTime {
          type rfc1213-mib:DisplayString;
          description
           "The time when the installed software was built.  (DateAndTime textual convention, from SNMPv2-TC)";
          smiv2:max-access read-only;
          smiv2:oid 1.3.6.1.4.1.1332.1.1.5.3.39.2.1.13;
        }

        leaf msanBoardConfSwBranch {
          type rfc1213-mib:DisplayString;
          description
           "The repository branch where the installed software was built from.";
          smiv2:max-access read-only;
          smiv2:oid 1.3.6.1.4.1.1332.1.1.5.3.39.2.1.14;
        }

        leaf msanBoardConfSwBuildReference {
          type rfc1213-mib:DisplayString;
          description
           "The repository reference number of the installed software build branch. ";
          smiv2:max-access read-only;
          smiv2:oid 1.3.6.1.4.1.1332.1.1.5.3.39.2.1.15;
        }
      }
    }

    container msanBoardListTable {
      description
       "Description.";
      smiv2:oid 1.3.6.1.4.1.1332.1.1.5.3.39.3;

      list msanBoardListEntry {
        key msanBoardListId;
        description
         "Description.";
        smiv2:oid 1.3.6.1.4.1.1332.1.1.5.3.39.3.1;

        leaf msanBoardListId {
          type rfc1213-mib:DisplayString;
          description
           "Identification of supported board (e.g. UTA6041BA).";
          smiv2:max-access read-only;
          smiv2:oid 1.3.6.1.4.1.1332.1.1.5.3.39.3.1.1;
        }

        leaf msanBoardListType {
          type rfc1213-mib:DisplayString;
          description
           "Type of physical board (e.g. IDC, SGO, SFA, ...).";
          smiv2:max-access read-only;
          smiv2:oid 1.3.6.1.4.1.1332.1.1.5.3.39.3.1.2;
        }
      }
    }

    container msanAppRateLimitTable {
      description
       "Description.";
      smiv2:oid 1.3.6.1.4.1.1332.1.1.5.3.41.2;

      list msanAppRateLimitEntry {
        key ifIndex;
        description
         "Description.";
        smiv2:oid 1.3.6.1.4.1.1332.1.1.5.3.41.2.1;

        leaf ifIndex {
          type leafref {
            path "/if-mib:interfaces/if-mib:ifEntry/if-mib:ifIndex";
          }
        }

        leaf msanAppRateLimitDhcp {
          type int32 {
            range "0..1000";
          }
          units pps;
          description
           "Maximum number of received DHCP packets in one second (pps) per interface.";
          smiv2:max-access read-write;
          smiv2:oid 1.3.6.1.4.1.1332.1.1.5.3.41.2.1.1;
        }

        leaf msanAppRateLimitDhcpState {
          type enumeration {
            enum enable {
              value 1;
            }
            enum disable {
              value 2;
            }
          }
          description
           "Administrative state of DHCP traffic rate limiting.";
          smiv2:defval enable;
          smiv2:max-access read-write;
          smiv2:oid 1.3.6.1.4.1.1332.1.1.5.3.41.2.1.2;
        }

        leaf msanAppRateLimitPppoe {
          type int32 {
            range "0..1000";
          }
          units pps;
          description
           "Maximum number of received PPPoE packets in one second (pps) per interface.";
          smiv2:max-access read-write;
          smiv2:oid 1.3.6.1.4.1.1332.1.1.5.3.41.2.1.3;
        }

        leaf msanAppRateLimitPppoeState {
          type enumeration {
            enum enable {
              value 1;
            }
            enum disable {
              value 2;
            }
          }
          description
           "Administrative state of PPPoE traffic rate limiting.";
          smiv2:max-access read-write;
          smiv2:oid 1.3.6.1.4.1.1332.1.1.5.3.41.2.1.4;
        }

        leaf msanAppRateLimitIgmp {
          type int32 {
            range "0..1000";
          }
          units pps;
          description
           "Maximum number of received DHCP packets in one second (pps) per interface.";
          smiv2:max-access read-write;
          smiv2:oid 1.3.6.1.4.1.1332.1.1.5.3.41.2.1.5;
        }

        leaf msanAppRateLimitIgmpState {
          type enumeration {
            enum enable {
              value 1;
            }
            enum disable {
              value 2;
            }
          }
          description
           "Administrative state of IGMP traffic rate limiting.";
          smiv2:max-access read-write;
          smiv2:oid 1.3.6.1.4.1.1332.1.1.5.3.41.2.1.6;
        }

        leaf msanAppRateLimitStp {
          type int32 {
            range "0..1000";
          }
          units pps;
          description
           "Maximum number of received STP packets in one second (pps) per interface.";
          smiv2:max-access read-write;
          smiv2:oid 1.3.6.1.4.1.1332.1.1.5.3.41.2.1.7;
        }

        leaf msanAppRateLimitStpState {
          type enumeration {
            enum enable {
              value 1;
            }
            enum disable {
              value 2;
            }
          }
          description
           "Administrative state of STP traffic rate limiting.";
          smiv2:max-access read-write;
          smiv2:oid 1.3.6.1.4.1.1332.1.1.5.3.41.2.1.8;
        }

        leaf msanAppRateLimitMn {
          type int32 {
            range "0..1000";
          }
          units pps;
          description
           "Maximum number of received MN packets (management traffic) in one second (pps) per interface.";
          smiv2:max-access read-write;
          smiv2:oid 1.3.6.1.4.1.1332.1.1.5.3.41.2.1.9;
        }

        leaf msanAppRateLimitMnState {
          type enumeration {
            enum enable {
              value 1;
            }
            enum disable {
              value 2;
            }
          }
          description
           "Administrative state of MN traffic rate limiting.";
          smiv2:max-access read-write;
          smiv2:oid 1.3.6.1.4.1.1332.1.1.5.3.41.2.1.10;
        }
      }
    }

    container msanMulticastIntfStaticGroupTable {
      status deprecated;
      description
       "The table attaches static multicast groups to the interfaces.";
      smiv2:oid 1.3.6.1.4.1.1332.1.1.5.3.100.2;

      list msanMulticastIntfStaticGroupEntry {
        key "ifIndex msanMulticastIntfStaticGroupIPAddr";
        status deprecated;
        description
         "Description.";
        smiv2:oid 1.3.6.1.4.1.1332.1.1.5.3.100.2.1;

        leaf ifIndex {
          type leafref {
            path "/if-mib:interfaces/if-mib:ifEntry/if-mib:ifIndex";
          }
        }

        leaf msanMulticastIntfStaticGroupIPAddr {
          type inet:ipv4-address;
          status deprecated;
          description
           "IP multicast address of valid multicast group.";
          smiv2:max-access not-accessible;
          smiv2:oid 1.3.6.1.4.1.1332.1.1.5.3.100.2.1.1;
        }

        leaf msanMulticastIntfStaticGroupRowStatus {
          type snmpv2-tc:RowStatus;
          status deprecated;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.100.2.1.2;
        }
      }
    }

    container msanMulticastGroupTable {
      description
       "Description.";
      smiv2:oid 1.3.6.1.4.1.1332.1.1.5.3.100.3;

      list msanMulticastGroupEntry {
        key "dot1qVlanIndex msanMulticastGroupIpAddr";
        description
         "Description.";
        smiv2:oid 1.3.6.1.4.1.1332.1.1.5.3.100.3.1;

        leaf dot1qVlanIndex {
          type leafref {
            path "/q-bridge:Q-BRIDGE-MIB/q-bridge:dot1qVlanCurrentTable/q-bridge:dot1qVlanCurrentEntry/q-bridge:dot1qVlanIndex";
          }
        }

        leaf msanMulticastGroupIpAddr {
          type inet:ipv4-address;
          description
           "IP multicast address of valid multicast group.";
          smiv2:max-access not-accessible;
          smiv2:oid 1.3.6.1.4.1.1332.1.1.5.3.100.3.1.1;
        }

        leaf msanMulticastGroupName {
          type binary;
          description
           "Name of multicast group.";
          smiv2:max-access read-write;
          smiv2:oid 1.3.6.1.4.1.1332.1.1.5.3.100.3.1.2;
        }
      }
    }

    container msanMulticastAclListTable {
      status deprecated;
      description
       "The table below assigns the symbolic names to the specific multicast ACLs.";
      smiv2:oid 1.3.6.1.4.1.1332.1.1.5.3.100.4;

      list msanMulticastAclListEntry {
        key msanMulticastAclListId;
        status deprecated;
        description
         "Description.";
        smiv2:oid 1.3.6.1.4.1.1332.1.1.5.3.100.4.1;

        leaf msanMulticastAclListId {
          type int32 {
            range "0..255";
          }
          status deprecated;
          description
           "Multicast List id. Integer from 0 to 255.";
          smiv2:max-access not-accessible;
          smiv2:oid 1.3.6.1.4.1.1332.1.1.5.3.100.4.1.1;
        }

        leaf msanMulticastAclListName {
          type snmp-framework:SnmpAdminString;
          status deprecated;
          description
           "ACL list symbolic name. Should be unique.";
          smiv2:max-access read-write;
          smiv2:oid 1.3.6.1.4.1.1332.1.1.5.3.100.4.1.2;
        }
      }
    }

    container msanMulticastAclListGroupTable {
      status deprecated;
      description
       "The table below links the multicast groups to the ACL.";
      smiv2:oid 1.3.6.1.4.1.1332.1.1.5.3.100.5;

      list msanMulticastAclListGroupEntry {
        key "msanMulticastAclListId msanMulticastAclGroupIpAddr";
        status deprecated;
        description
         "Description.";
        smiv2:oid 1.3.6.1.4.1.1332.1.1.5.3.100.5.1;

        leaf msanMulticastAclListId {
          type leafref {
            path "/iskratel-msan:ISKRATEL-MSAN-MIB/iskratel-msan:msanMulticastAclListTable/iskratel-msan:msanMulticastAclListEntry/iskratel-msan:msanMulticastAclListId";
          }
          status deprecated;
        }

        leaf msanMulticastAclGroupIpAddr {
          type inet:ipv4-address;
          status deprecated;
          description
           "IP multicast address of valid ACL multicast group.";
          smiv2:max-access not-accessible;
          smiv2:oid 1.3.6.1.4.1.1332.1.1.5.3.100.5.1.1;
        }
      }
    }

    container msanMulticastAclIntfListTable {
      status deprecated;
      description
       "The table below assigns the multicast ACL to the interfaces";
      smiv2:oid 1.3.6.1.4.1.1332.1.1.5.3.100.6;

      list msanMulticastAclIntfListEntry {
        key "ifIndex msanMulticastAclListId";
        status deprecated;
        description
         "Description.";
        smiv2:oid 1.3.6.1.4.1.1332.1.1.5.3.100.6.1;

        leaf ifIndex {
          type leafref {
            path "/if-mib:interfaces/if-mib:ifEntry/if-mib:ifIndex";
          }
        }

        leaf msanMulticastAclListId {
          type leafref {
            path "/iskratel-msan:ISKRATEL-MSAN-MIB/iskratel-msan:msanMulticastAclListTable/iskratel-msan:msanMulticastAclListEntry/iskratel-msan:msanMulticastAclListId";
          }
          status deprecated;
        }

        leaf msanMulticastAclIntfListMode {
          type enumeration {
            enum accept {
              value 1;
            }
            enum deny {
              value 2;
            }
          }
          status deprecated;
          description
           "Defines the mode in which interface for specified ACL list works.";
          smiv2:max-access read-write;
          smiv2:oid 1.3.6.1.4.1.1332.1.1.5.3.100.6.1.1;
        }
      }
    }

    container msanMulticastAclListVlanGroupTable {
      status deprecated;
      description
       "The table below links the multicast groups to the ACL.";
      smiv2:oid 1.3.6.1.4.1.1332.1.1.5.3.100.7;

      list msanMulticastAclListVlanGroupEntry {
        key "msanMulticastAclListId dot1qVlanIndex msanMulticastAclListVlanGroupIpAddr";
        status deprecated;
        description
         "Description.";
        smiv2:oid 1.3.6.1.4.1.1332.1.1.5.3.100.7.1;

        leaf msanMulticastAclListId {
          type leafref {
            path "/iskratel-msan:ISKRATEL-MSAN-MIB/iskratel-msan:msanMulticastAclListTable/iskratel-msan:msanMulticastAclListEntry/iskratel-msan:msanMulticastAclListId";
          }
          status deprecated;
        }

        leaf dot1qVlanIndex {
          type leafref {
            path "/q-bridge:Q-BRIDGE-MIB/q-bridge:dot1qVlanCurrentTable/q-bridge:dot1qVlanCurrentEntry/q-bridge:dot1qVlanIndex";
          }
        }

        leaf msanMulticastAclListVlanGroupIpAddr {
          type inet:ipv4-address;
          status deprecated;
          description
           "IP multicast address of valid ACL multicast group.";
          smiv2:max-access not-accessible;
          smiv2:oid 1.3.6.1.4.1.1332.1.1.5.3.100.7.1.1;
        }

        leaf msanMulticastAclListVlanGroupRowStatus {
          type snmpv2-tc:RowStatus;
          status deprecated;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.100.7.1.2;
        }
      }
    }

    container msanMulticastIntfVlanStaticGroupTable {
      description
       "Description.";
      smiv2:oid 1.3.6.1.4.1.1332.1.1.5.3.100.8;

      list msanMulticastIntfVlanStaticGroupEntry {
        key "ifIndex dot1qVlanIndex msanMulticastIntfVlanStaticGroupIpAddr";
        description
         "Description.";
        smiv2:oid 1.3.6.1.4.1.1332.1.1.5.3.100.8.1;

        leaf ifIndex {
          type leafref {
            path "/if-mib:interfaces/if-mib:ifEntry/if-mib:ifIndex";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanMulticastIntfVlanStaticGroupIpAddr {
          type inet:ipv4-address;
          description
           "IP multicast address of valid multicast group.";
          smiv2:max-access not-accessible;
          smiv2:oid 1.3.6.1.4.1.1332.1.1.5.3.100.8.1.1;
        }

        leaf msanMulticastIntfVlanStaticGroupRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.100.8.1.2;
        }
      }
    }

    container msanMulticastAccessListTable {
      description
       "The table below assigns the symbolic names to the specific multicast ACLs.";
      smiv2:oid 1.3.6.1.4.1.1332.1.1.5.3.100.9;

      list msanMulticastAccessListEntry {
        key msanMulticastAccessListName;
        description
         "Description.";
        smiv2:oid 1.3.6.1.4.1.1332.1.1.5.3.100.9.1;

        leaf msanMulticastAccessListName {
          type binary {
            length "1..32";
          }
          description
           "ACL list symbolic name. Should be unique.";
          smiv2:max-access not-accessible;
          smiv2:oid 1.3.6.1.4.1.1332.1.1.5.3.100.9.1.1;
        }
      }
    }

    container msanMulticastAccessListGroupTable {
      description
       "The table below links the multicast addresses to the ACL list";
      smiv2:oid 1.3.6.1.4.1.1332.1.1.5.3.100.10;

      list msanMulticastAccessListGroupEntry {
        key "msanMulticastAccessListName dot1qVlanIndex msanMulticastAccessListGroupIpAddr";
        description
         "Description.";
        smiv2:oid 1.3.6.1.4.1.1332.1.1.5.3.100.10.1;

        leaf msanMulticastAccessListName {
          type leafref {
            path "/iskratel-msan:ISKRATEL-MSAN-MIB/iskratel-msan:msanMulticastAccessListTable/iskratel-msan:msanMulticastAccessListEntry/iskratel-msan:msanMulticastAccessListName";
          }
        }

        leaf dot1qVlanIndex {
          type leafref {
            path "/q-bridge:Q-BRIDGE-MIB/q-bridge:dot1qVlanCurrentTable/q-bridge:dot1qVlanCurrentEntry/q-bridge:dot1qVlanIndex";
          }
        }

        leaf msanMulticastAccessListGroupIpAddr {
          type inet:ipv4-address;
          description
           "IP multicast address of valid ACL multicast group.";
          smiv2:max-access not-accessible;
          smiv2:oid 1.3.6.1.4.1.1332.1.1.5.3.100.10.1.1;
        }
      }
    }

    container msanMulticastAccessListIntfTable {
      description
       "The table below assigns the multicast ACL list to the interfaces";
      smiv2:oid 1.3.6.1.4.1.1332.1.1.5.3.100.11;

      list msanMulticastAccessListIntfEntry {
        key "ifName msanMulticastAccessListName";
        description
         "Description.";
        smiv2:oid 1.3.6.1.4.1.1332.1.1.5.3.100.11.1;

        leaf ifName {
          type if:interface-ref;
          description
            "A reference to the name of a configured network layer
             interface.";
        }

        leaf msanMulticastAccessListName {
          type leafref {
            path "/iskratel-msan:ISKRATEL-MSAN-MIB/iskratel-msan:msanMulticastAccessListTable/iskratel-msan:msanMulticastAccessListEntry/iskratel-msan:msanMulticastAccessListName";
          }
        }

        leaf msanMulticastAccessListIntfMode {
          type enumeration {
            enum accept {
              value 1;
            }
            enum deny {
              value 2;
            }
          }
          description
           "Defines the mode in which interface for specified ACL list works.";
          smiv2:max-access read-write;
          smiv2:oid 1.3.6.1.4.1.1332.1.1.5.3.100.11.1.1;
        }
      }
    }

    container msanSwitchMFDBTable {
      description
       "The Multicast Forwarding Database table";
      smiv2:oid 1.3.6.1.4.1.1332.1.1.5.3.100.12;

      list msanSwitchMFDBEntry {
        key "msanSwitchMFDBProtocolType msanSwitchMFDBVlanId msanSwitchMFDBMacAddress";
        description
         "Contains Forwarding and Filtering information per Component User, Vlan Index, and MAC Address.";
        smiv2:oid 1.3.6.1.4.1.1332.1.1.5.3.100.12.1;

        leaf msanSwitchMFDBProtocolType {
          type enumeration {
            enum static {
              value 1;
            }
            enum gmrp {
              value 2;
            }
            enum igmp {
              value 3;
            }
          }
          description
           "The component that is responsible for this entry in the Multicast
            Forwarding Database.";
          smiv2:max-access read-only;
          smiv2:oid 1.3.6.1.4.1.1332.1.1.5.3.100.12.1.1;
        }

        leaf msanSwitchMFDBVlanId {
          type q-bridge:VlanIndex;
          description
           "Vlan Index for which this entry is associated with.";
          smiv2:max-access read-only;
          smiv2:oid 1.3.6.1.4.1.1332.1.1.5.3.100.12.1.2;
        }

        leaf msanSwitchMFDBMacAddress {
          type yang:mac-address;
          description
           "A multicast MAC address for which the switch has forwarding and or
            filtering information.";
          smiv2:max-access read-only;
          smiv2:oid 1.3.6.1.4.1.1332.1.1.5.3.100.12.1.3;
        }

        leaf msanSwitchMFDBType {
          type enumeration {
            enum static {
              value 1;
            }
            enum dynamic {
              value 2;
            }
          }
          description
           "This displays the type of the entry.
            
            static(1)  - Entries configured by the end user
            dynamic(2) - Entries added as a result of a learning process or protocol";
          smiv2:max-access read-only;
          smiv2:oid 1.3.6.1.4.1.1332.1.1.5.3.100.12.1.4;
        }

        leaf msanSwitchMFDBDescription {
          type rfc1213-mib:DisplayString;
          description
           "Text description of this multicast table entry.";
          smiv2:max-access read-only;
          smiv2:oid 1.3.6.1.4.1.1332.1.1.5.3.100.12.1.5;
        }

        leaf msanSwitchMFDBForwardingPortMask {
          type iskratel-msan:PortMask;
          description
           "BitMask indicating which ports this entry indicates should be forwarded.
            
            To obtain port numbers from interface numbers, use the objects
            agentPortDot1dBasePort and agentPortIfIndex in the agentPortConfigTable
            table.";
          smiv2:max-access read-only;
          smiv2:oid 1.3.6.1.4.1.1332.1.1.5.3.100.12.1.6;
        }

        leaf msanSwitchMFDBFilteringPortMask {
          type iskratel-msan:PortMask;
          description
           "BitMask indicating which ports this entry indicates should be filtered.
            
            To obtain port numbers from interface numbers, use the objects
            agentPortDot1dBasePort and agentPortIfIndex in the agentPortConfigTable
            table.";
          smiv2:max-access read-only;
          smiv2:oid 1.3.6.1.4.1.1332.1.1.5.3.100.12.1.7;
        }
      }
    }

    container msanMulticastStaticClientTable {
      description
       "Description.";
      smiv2:oid 1.3.6.1.4.1.1332.1.1.5.3.100.13;

      list msanMulticastStaticClientEntry {
        key "dot1qVlanIndex msanMulticastStaticClientIpAddr";
        description
         "Description.";
        smiv2:oid 1.3.6.1.4.1.1332.1.1.5.3.100.13.1;

        leaf dot1qVlanIndex {
          type leafref {
            path "/q-bridge:Q-BRIDGE-MIB/q-bridge:dot1qVlanCurrentTable/q-bridge:dot1qVlanCurrentEntry/q-bridge:dot1qVlanIndex";
          }
        }

        leaf msanMulticastStaticClientIpAddr {
          type inet:ipv4-address;
          description
           "Multicast static client IP address on specified vlan_id.";
          smiv2:max-access not-accessible;
          smiv2:oid 1.3.6.1.4.1.1332.1.1.5.3.100.13.1.1;
        }

        leaf msanMulticastStaticClientRowStatus {
          type snmpv2-tc:RowStatus;
          description
           "The row status object controls the creation/deletion of rows in this table.
            Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.100.13.1.2;
        }
      }
    }

    container msanFilteringFilterTable {
      status deprecated;
      description
       "Defines a list of filters.";
      smiv2:oid 1.3.6.1.4.1.1332.1.1.5.3.101.3;

      list msanFilteringFilterEntry {
        key msanFilteringFilterId;
        status deprecated;
        description
         "Description.";
        smiv2:oid 1.3.6.1.4.1.1332.1.1.5.3.101.3.1;

        leaf msanFilteringFilterId {
          type int32 {
            range "1..64|301..500";
          }
          status deprecated;
          description
           "Filter identity.";
          smiv2:max-access read-write;
          smiv2:oid 1.3.6.1.4.1.1332.1.1.5.3.101.3.1.1;
        }

        leaf msanFilteringFilterName {
          type binary;
          status deprecated;
          description
           "Name of filter to be shown.";
          smiv2:max-access read-write;
          smiv2:oid 1.3.6.1.4.1.1332.1.1.5.3.101.3.1.2;
        }

        leaf msanFilteringFilterType {
          type enumeration {
            enum static {
              value 1;
            }
            enum dynamic {
              value 2;
            }
          }
          status deprecated;
          description
           "Type of filter (static or dynamic).";
          smiv2:max-access read-only;
          smiv2:oid 1.3.6.1.4.1.1332.1.1.5.3.101.3.1.3;
        }

        leaf msanFilteringFilterRowStatus {
          type snmpv2-tc:RowStatus;
          status deprecated;
          description
           "SNMP row status.
            
            Supported values:
            active(1) - valid entry;
            createAndGo(4) - used to create a new entry;
            destroy(6) - removes the entry.";
          smiv2:defval active;
          smiv2:max-access read-write;
          smiv2:oid 1.3.6.1.4.1.1332.1.1.5.3.101.3.1.4;
        }
      }
    }

    container msanFilteringAssignFilterTable {
      status deprecated;
      description
       "This table defines a list of filters assigned to interface.";
      smiv2:oid 1.3.6.1.4.1.1332.1.1.5.3.101.4;

      list msanFilteringAssignFilterEntry {
        key "ifIndex msanFilteringFilterId";
        status deprecated;
        description
         "Description.";
        smiv2:oid 1.3.6.1.4.1.1332.1.1.5.3.101.4.1;

        leaf ifIndex {
          type leafref {
            path "/if-mib:interfaces/if-mib:ifEntry/if-mib:ifIndex";
          }
        }

        leaf msanFilteringFilterId {
          type leafref {
            path "/iskratel-msan:ISKRATEL-MSAN-MIB/iskratel-msan:msanFilteringFilterTable/iskratel-msan:msanFilteringFilterEntry/iskratel-msan:msanFilteringFilterId";
          }
          status deprecated;
        }

        leaf msanFilteringAssignFilterVid {
          type int32 {
            range "0..4094";
          }
          status deprecated;
          description
           "ID of VLAN to be filtered.";
          smiv2:max-access read-write;
          smiv2:oid 1.3.6.1.4.1.1332.1.1.5.3.101.4.1.1;
        }

        leaf msanFilteringAssignFilterCos {
          type int32 {
            range "0..7";
          }
          status deprecated;
          description
           "CoS value to be filtered.";
          smiv2:max-access read-write;
          smiv2:oid 1.3.6.1.4.1.1332.1.1.5.3.101.4.1.2;
        }

        leaf msanFilteringAssignFilterDscp {
          type int32 {
            range "0..63";
          }
          status deprecated;
          description
           "DSCP field.";
          smiv2:max-access read-write;
          smiv2:oid 1.3.6.1.4.1.1332.1.1.5.3.101.4.1.3;
        }

        leaf msanFilteringAssignFilterPrec {
          type int32 {
            range "0..7";
          }
          status deprecated;
          description
           "Precedence in DSCP tag.";
          smiv2:max-access read-write;
          smiv2:oid 1.3.6.1.4.1.1332.1.1.5.3.101.4.1.4;
        }

        leaf msanFilteringAssignFilterRowStatus {
          type snmpv2-tc:RowStatus;
          status deprecated;
          description
           "SNMP row status.
            
            Supported values:
            active(1) - valid entry;
            createAndGo(4) - used to create a new entry;
            destroy(6) - removes the entry.";
          smiv2:defval active;
          smiv2:max-access read-write;
          smiv2:oid 1.3.6.1.4.1.1332.1.1.5.3.101.4.1.5;
        }
      }
    }

    container msanFilteringRuleTable {
      status deprecated;
      description
       "This table defines a list of filtering rules associated to filters.";
      smiv2:oid 1.3.6.1.4.1.1332.1.1.5.3.101.5;

      list msanFilteringRuleEntry {
        key "msanFilteringRuleId msanFilteringFilterId";
        status deprecated;
        description
         "Description.";
        smiv2:oid 1.3.6.1.4.1.1332.1.1.5.3.101.5.1;

        leaf msanFilteringFilterId {
          type leafref {
            path "/iskratel-msan:ISKRATEL-MSAN-MIB/iskratel-msan:msanFilteringFilterTable/iskratel-msan:msanFilteringFilterEntry/iskratel-msan:msanFilteringFilterId";
          }
          status deprecated;
        }

        leaf msanFilteringRuleId {
          type int32 {
            range "1..65535";
          }
          status deprecated;
          description
           "Filtering rule identity.";
          smiv2:max-access read-only;
          smiv2:oid 1.3.6.1.4.1.1332.1.1.5.3.101.5.1.1;
        }

        leaf msanFilteringRuleResponse {
          type enumeration {
            enum accept {
              value 1;
            }
            enum deny {
              value 2;
            }
          }
          status deprecated;
          description
           "Filter response.";
          smiv2:max-access read-write;
          smiv2:oid 1.3.6.1.4.1.1332.1.1.5.3.101.5.1.2;
        }

        leaf msanFilteringRuleFromMac {
          type yang:mac-address;
          status deprecated;
          description
           "Source Ethernet address.";
          smiv2:max-access read-write;
          smiv2:oid 1.3.6.1.4.1.1332.1.1.5.3.101.5.1.3;
        }

        leaf msanFilteringRuleFromMacMask {
          type yang:mac-address;
          status deprecated;
          description
           "Source Ethernet address mask.";
          smiv2:max-access read-write;
          smiv2:oid 1.3.6.1.4.1.1332.1.1.5.3.101.5.1.4;
        }

        leaf msanFilteringRuleFromIp {
          type inet:ipv4-address;
          status deprecated;
          description
           "Source IP address.";
          smiv2:max-access read-write;
          smiv2:oid 1.3.6.1.4.1.1332.1.1.5.3.101.5.1.5;
        }

        leaf msanFilteringRuleFromMask {
          type inet:ipv4-address;
          status deprecated;
          description
           "Source IP address mask.";
          smiv2:max-access read-write;
          smiv2:oid 1.3.6.1.4.1.1332.1.1.5.3.101.5.1.6;
        }

        leaf msanFilteringRuleFromPortLow {
          type uint32 {
            range "0..65535";
          }
          status deprecated;
          description
           "The lowest number of a source TCP or UDP port.";
          smiv2:max-access read-write;
          smiv2:oid 1.3.6.1.4.1.1332.1.1.5.3.101.5.1.7;
        }

        leaf msanFilteringRuleFromPortHigh {
          type uint32 {
            range "0..65535";
          }
          status deprecated;
          description
           "The highest number of a source TCP or UDP port..";
          smiv2:max-access read-write;
          smiv2:oid 1.3.6.1.4.1.1332.1.1.5.3.101.5.1.8;
        }

        leaf msanFilteringRuleToMac {
          type yang:mac-address;
          status deprecated;
          description
           "Destination Ethernet address.";
          smiv2:max-access read-write;
          smiv2:oid 1.3.6.1.4.1.1332.1.1.5.3.101.5.1.9;
        }

        leaf msanFilteringRuleToMacMask {
          type yang:mac-address;
          status deprecated;
          description
           "Destination Ethernet address mask.";
          smiv2:max-access read-write;
          smiv2:oid 1.3.6.1.4.1.1332.1.1.5.3.101.5.1.10;
        }

        leaf msanFilteringRuleToIp {
          type inet:ipv4-address;
          status deprecated;
          description
           "Destination IP address.";
          smiv2:max-access read-write;
          smiv2:oid 1.3.6.1.4.1.1332.1.1.5.3.101.5.1.11;
        }

        leaf msanFilteringRuleToMask {
          type inet:ipv4-address;
          status deprecated;
          description
           "Destination IP address mask.";
          smiv2:max-access read-write;
          smiv2:oid 1.3.6.1.4.1.1332.1.1.5.3.101.5.1.12;
        }

        leaf msanFilteringRuleToPortLow {
          type uint32 {
            range "0..65535";
          }
          status deprecated;
          description
           "The lowest number of a destination TCP or UDP port.";
          smiv2:max-access read-write;
          smiv2:oid 1.3.6.1.4.1.1332.1.1.5.3.101.5.1.13;
        }

        leaf msanFilteringRuleToPortHigh {
          type uint32 {
            range "0..65535";
          }
          status deprecated;
          description
           "The highest number of a destination TCP or UDP port.";
          smiv2:max-access read-write;
          smiv2:oid 1.3.6.1.4.1.1332.1.1.5.3.101.5.1.14;
        }

        leaf msanFilteringRuleEtherProto {
          type binary;
          status deprecated;
          description
           "Ethernet protocol to be filtered.";
          smiv2:max-access read-write;
          smiv2:oid 1.3.6.1.4.1.1332.1.1.5.3.101.5.1.15;
        }

        leaf msanFilteringRuleIpProto {
          type binary;
          status deprecated;
          description
           "IP protocol to be filtered.";
          smiv2:max-access read-write;
          smiv2:oid 1.3.6.1.4.1.1332.1.1.5.3.101.5.1.16;
        }

        leaf msanFilteringRuleIcmType {
          type uint32 {
            range "0..255";
          }
          status deprecated;
          description
           "ICMP type. ICMP sends an error message to the transmitter of IP packets and provides
            information at IP packet processing.";
          smiv2:max-access read-write;
          smiv2:oid 1.3.6.1.4.1.1332.1.1.5.3.101.5.1.17;
        }

        leaf msanFilteringRulePrec {
          type uint32 {
            range "0..7";
          }
          status deprecated;
          description
           "Precedence in DSCP tag.";
          smiv2:max-access read-write;
          smiv2:oid 1.3.6.1.4.1.1332.1.1.5.3.101.5.1.18;
        }

        leaf msanFilteringRuleTos {
          type uint32 {
            range "0..15";
          }
          status deprecated;
          description
           "TOS to be filtered.";
          smiv2:max-access read-write;
          smiv2:oid 1.3.6.1.4.1.1332.1.1.5.3.101.5.1.19;
        }

        leaf msanFilteringRuleVid {
          type uint32 {
            range "0..4094";
          }
          status deprecated;
          description
           "ID of VLAN to be filtered.";
          smiv2:max-access read-write;
          smiv2:oid 1.3.6.1.4.1.1332.1.1.5.3.101.5.1.20;
        }

        leaf msanFilteringRuleCos {
          type uint32 {
            range "0..7";
          }
          status deprecated;
          description
           "CoS value to be filtered.";
          smiv2:max-access read-write;
          smiv2:oid 1.3.6.1.4.1.1332.1.1.5.3.101.5.1.21;
        }

        leaf msanFilteringRuleTag {
          type enumeration {
            enum untagged {
              value 1;
            }
            enum tagged {
              value 2;
            }
            enum qinq-tagged {
              value 3;
            }
          }
          status deprecated;
          description
           "802.1Q tag.";
          smiv2:max-access read-write;
          smiv2:oid 1.3.6.1.4.1.1332.1.1.5.3.101.5.1.22;
        }

        leaf msanFilteringRuleRowStatus {
          type snmpv2-tc:RowStatus;
          status deprecated;
          description
           "SNMP row status.
            
            Supported values:
            active(1) - valid entry;
            createAndGo(4) - used to create a new entry;
            destroy(6) - removes the entry.";
          smiv2:defval active;
          smiv2:max-access read-write;
          smiv2:oid 1.3.6.1.4.1.1332.1.1.5.3.101.5.1.23;
        }
      }
    }

    container msanFilteringAttachedFilterTable {
      status deprecated;
      description
       "This table defines information about filters attached to interface.";
      smiv2:oid 1.3.6.1.4.1.1332.1.1.5.3.101.6;

      list msanFilteringAttachedFilterEntry {
        key "ifIndex msanFilteringFilterId";
        status deprecated;
        description
         "Description.";
        smiv2:oid 1.3.6.1.4.1.1332.1.1.5.3.101.6.1;

        leaf ifIndex {
          type leafref {
            path "/if-mib:interfaces/if-mib:ifEntry/if-mib:ifIndex";
          }
        }

        leaf msanFilteringFilterId {
          type leafref {
            path "/iskratel-msan:ISKRATEL-MSAN-MIB/iskratel-msan:msanFilteringFilterTable/iskratel-msan:msanFilteringFilterEntry/iskratel-msan:msanFilteringFilterId";
          }
          status deprecated;
        }

        leaf msanFilteringAttachedFilterDirect {
          type enumeration {
            enum in {
              value 1;
            }
            enum out {
              value 2;
            }
          }
          status deprecated;
          description
           "Point of attaching a filter.";
          smiv2:max-access read-write;
          smiv2:oid 1.3.6.1.4.1.1332.1.1.5.3.101.6.1.1;
        }

        leaf msanFilteringAttachedFilterRowStatus {
          type snmpv2-tc:RowStatus;
          status deprecated;
          description
           "SNMP row status.
            
            Supported values:
            active(1) - valid entry;
            createAndGo(4) - used to create a new entry;
            destroy(6) - removes the entry.";
          smiv2:max-access read-write;
          smiv2:oid 1.3.6.1.4.1.1332.1.1.5.3.101.6.1.2;
        }
      }
    }

    container msanBridgeCCXTable {
      status deprecated;
      description
       "The table contents the information about all CCX pairs.";
      smiv2:oid 1.3.6.1.4.1.1332.1.1.5.3.102.2;

      list msanBridgeCCXEntry {
        key "msanBridgeCCXInterface1 msanBridgeCCXInterface2";
        status deprecated;
        description
         "Description.";
        smiv2:oid 1.3.6.1.4.1.1332.1.1.5.3.102.2.1;

        leaf msanBridgeCCXInterface1 {
          type if-mib:InterfaceIndex;
          status deprecated;
          description
           "The first interface to make cross-connection exchange";
          smiv2:max-access read-write;
          smiv2:oid 1.3.6.1.4.1.1332.1.1.5.3.102.2.1.1;
        }

        leaf msanBridgeCCXInterface2 {
          type if-mib:InterfaceIndex;
          status deprecated;
          description
           "The second interface to make cross-connection exchange";
          smiv2:max-access read-write;
          smiv2:oid 1.3.6.1.4.1.1332.1.1.5.3.102.2.1.2;
        }

        leaf msanBridgeCCXRowStatus {
          type snmpv2-tc:RowStatus;
          status deprecated;
          description
           "The row status object controls the creation/deletion of rows in this table. Its semantics are the same as those for the RowStatus textual convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.102.2.1.3;
        }
      }
    }

    container msanIPSGIntfTable {
      description
       "Description.";
      smiv2:oid 1.3.6.1.4.1.1332.1.1.5.3.103.2;

      list msanIPSGIntfEntry {
        key ifIndex;
        description
         "Description.";
        smiv2:oid 1.3.6.1.4.1.1332.1.1.5.3.103.2.1;

        leaf ifIndex {
          type leafref {
            path "/if-mib:interfaces/if-mib:ifEntry/if-mib:ifIndex";
          }
        }

        leaf msanIPSGIntfAdminMode {
          type enumeration {
            enum enable {
              value 1;
            }
            enum disable {
              value 2;
            }
          }
          description
           "Enable/disable IP Source Guard for the selected interface.";
          smiv2:defval disable;
          smiv2:max-access read-write;
          smiv2:oid 1.3.6.1.4.1.1332.1.1.5.3.103.2.1.1;
        }

        leaf msanIPSGIntfBindsLimit {
          type int32 {
            range "0..15";
          }
          description
           "IPSG binding limit for DHCPv4 snooping table per interface.
            Value 0 defines there is no limit.";
          smiv2:defval 4;
          smiv2:max-access read-write;
          smiv2:oid 1.3.6.1.4.1.1332.1.1.5.3.103.2.1.2;
        }

        leaf msanIPSGIntfFilteringMode {
          type enumeration {
            enum iponly {
              value 1;
            }
            enum ipmac {
              value 2;
            }
          }
          description
           "Sets the traffic filtering type. Traffic can be filtered either by IP or by both IP and MAC address.";
          smiv2:defval iponly;
          smiv2:max-access read-write;
          smiv2:oid 1.3.6.1.4.1.1332.1.1.5.3.103.2.1.3;
        }

        leaf msanIPSGIntfIpv6AdminMode {
          type enumeration {
            enum enable {
              value 1;
            }
            enum disable {
              value 2;
            }
          }
          description
           "Enable/disable IPv6 Source Guard for the selected interface.";
          smiv2:defval disable;
          smiv2:max-access read-write;
          smiv2:oid 1.3.6.1.4.1.1332.1.1.5.3.103.2.1.4;
        }

        leaf msanIPSGIntfBindsLimitDhcpv6 {
          type int32 {
            range "0..15";
          }
          description
           "IPSG binding limit for DHCPv6 (IPv6 DHCP)snooping table per interface.
            Value 0 defines there is no limit.";
          smiv2:defval 4;
          smiv2:max-access read-write;
          smiv2:oid 1.3.6.1.4.1.1332.1.1.5.3.103.2.1.5;
        }

        leaf msanIPSGIntfBindsLimitND {
          type int32 {
            range "0..15";
          }
          description
           "IPSG binding limit for ND (IPv6 Neighbor Discovery) snooping table per interface
            Value 0 defines there is no limit.";
          smiv2:defval 4;
          smiv2:max-access read-write;
          smiv2:oid 1.3.6.1.4.1.1332.1.1.5.3.103.2.1.6;
        }

        leaf msanIPSGIntfClearDynamicBinds {
          type enumeration {
            enum disable {
              value 1;
            }
            enum clear-all {
              value 2;
            }
            enum clear-dhcpv4 {
              value 3;
            }
            enum clear-dhcpv6 {
              value 4;
            }
            enum clear-nd {
              value 5;
            }
          }
          description
           "Clear IPSG snooping tables per interface";
          smiv2:max-access read-write;
          smiv2:oid 1.3.6.1.4.1.1332.1.1.5.3.103.2.1.7;
        }
      }
    }

    container msanIPSGBindingsTable {
      status deprecated;
      description
       "DThe table for storing IP source binding";
      smiv2:oid 1.3.6.1.4.1.1332.1.1.5.3.103.3;

      list msanIPSGBindingsEntry {
        key "ifIndex msanIPSGBindVlan msanIPSGBindMac";
        status deprecated;
        description
         "Description.";
        smiv2:oid 1.3.6.1.4.1.1332.1.1.5.3.103.3.1;

        leaf ifIndex {
          type leafref {
            path "/if-mib:interfaces/if-mib:ifEntry/if-mib:ifIndex";
          }
        }

        leaf msanIPSGBindIp {
          type inet:ipv4-address;
          status deprecated;
          description
           "Allowed IP address";
          smiv2:max-access read-write;
          smiv2:oid 1.3.6.1.4.1.1332.1.1.5.3.103.3.1.1;
        }

        leaf msanIPSGBindVlan {
          type q-bridge:VlanIndex;
          status deprecated;
          description
           "Allowed VLAN number";
          smiv2:max-access read-only;
          smiv2:oid 1.3.6.1.4.1.1332.1.1.5.3.103.3.1.2;
        }

        leaf msanIPSGBindMac {
          type yang:mac-address;
          status deprecated;
          description
           "Allowed MAC address";
          smiv2:max-access read-only;
          smiv2:oid 1.3.6.1.4.1.1332.1.1.5.3.103.3.1.3;
        }

        leaf msanIPSGBindLeaseRemainingTime {
          type yang:timeticks;
          status deprecated;
          description
           "The period for which the DHCP lease is valid.
            It is displayed in days, hours, minutes, and seconds.
            
            For static IPSG bindings this value is set to 0 (infinitive).";
          smiv2:max-access read-only;
          smiv2:oid 1.3.6.1.4.1.1332.1.1.5.3.103.3.1.4;
        }

        leaf msanIPSGBindType {
          type enumeration {
            enum static {
              value 1;
            }
            enum dynamic {
              value 2;
            }
          }
          status deprecated;
          description
           "Type of IPSG binding.";
          smiv2:max-access read-only;
          smiv2:oid 1.3.6.1.4.1.1332.1.1.5.3.103.3.1.5;
        }

        leaf msanIPSGBindMatchedFrames {
          type yang:counter32;
          status deprecated;
          description
           "Number of matched frames for selected IPSG binding.";
          smiv2:max-access read-only;
          smiv2:oid 1.3.6.1.4.1.1332.1.1.5.3.103.3.1.6;
        }

        leaf msanIPSGBindRowStatus {
          type snmpv2-tc:RowStatus;
          status deprecated;
          description
           "The row status object controls the creation/deletion of rows in this table.
            Its semantics are the same as those for the RowStatus textual convention specified for SNMPv2.
            For row creation use createAndWait(5).
            For row activation use active(1).
            For row deletion use destroy(6).
            
            Other values are currently not supported.
            
            For row activation next terms must be accomplished:
            - msanIPSGBindIp must be defined ";
          smiv2:max-access read-write;
          smiv2:oid 1.3.6.1.4.1.1332.1.1.5.3.103.3.1.7;
        }
      }
    }

    container msanIPSGIpv4PortStaticBindTable {
      description
       "Description.";
      smiv2:oid 1.3.6.1.4.1.1332.1.1.5.3.103.4;

      list msanIPSGIpv4PortStaticBindEntry {
        key "ifIndex msanIPSGIpv4PortStaticBindMacAddress msanIPSGIpv4PortStaticBindVlanId msanIPSGIpv4PortStaticBindIpAddress";
        description
         "Description.";
        smiv2:oid 1.3.6.1.4.1.1332.1.1.5.3.103.4.1;

        leaf ifIndex {
          type leafref {
            path "/if-mib:interfaces/if-mib:ifEntry/if-mib:ifIndex";
          }
        }

        leaf msanIPSGIpv4PortStaticBindMacAddress {
          type yang:mac-address;
          description
           "Allowed MAC address";
          smiv2:max-access not-accessible;
          smiv2:oid 1.3.6.1.4.1.1332.1.1.5.3.103.4.1.1;
        }

        leaf msanIPSGIpv4PortStaticBindVlanId {
          type q-bridge:VlanIndex;
          description
           "Allowed VLAN number";
          smiv2:max-access not-accessible;
          smiv2:oid 1.3.6.1.4.1.1332.1.1.5.3.103.4.1.2;
        }

        leaf msanIPSGIpv4PortStaticBindIpAddress {
          type inet-address:InetAddressIPv4;
          description
           "Allowed IPv4 address";
          smiv2:max-access not-accessible;
          smiv2:oid 1.3.6.1.4.1.1332.1.1.5.3.103.4.1.3;
        }

        leaf msanIPSGIpv4PortStaticBindMatchedFrames {
          type yang:counter32;
          description
           "Number of matched frames for selected IPSG binding.";
          smiv2:max-access read-only;
          smiv2:oid 1.3.6.1.4.1.1332.1.1.5.3.103.4.1.4;
        }

        leaf msanIPSGIpv4PortStaticBindRowStatus {
          type snmpv2-tc:RowStatus;
          description
           "The row status object controls the creation/deletion of rows in this table.
            Its semantics are the same as those for the RowStatus textual convention specified for SNMPv2.
            For row creation use createAndGo(4).
            For row activation use active(1).
            For row deletion use destroy(6).
            
            Other values are currently not supported.";
          smiv2:max-access read-write;
          smiv2:oid 1.3.6.1.4.1.1332.1.1.5.3.103.4.1.5;
        }
      }
    }

    container msanIPSGIpv6PortStaticBindTable {
      description
       "Description.";
      smiv2:oid 1.3.6.1.4.1.1332.1.1.5.3.103.5;

      list msanIPSGIpv6PortStaticBindEntry {
        key "ifIndex msanIPSGIpv6PortStaticBindMacAddress msanIPSGIpv6PortStaticBindVlanId msanIPSGIpv6PortStaticBindIpAddress";
        description
         "Description.";
        smiv2:oid 1.3.6.1.4.1.1332.1.1.5.3.103.5.1;

        leaf ifIndex {
          type leafref {
            path "/if-mib:interfaces/if-mib:ifEntry/if-mib:ifIndex";
          }
        }

        leaf msanIPSGIpv6PortStaticBindMacAddress {
          type yang:mac-address;
          description
           "Allowed MAC address";
          smiv2:max-access not-accessible;
          smiv2:oid 1.3.6.1.4.1.1332.1.1.5.3.103.5.1.1;
        }

        leaf msanIPSGIpv6PortStaticBindVlanId {
          type q-bridge:VlanIndex;
          description
           "Allowed VLAN number";
          smiv2:max-access not-accessible;
          smiv2:oid 1.3.6.1.4.1.1332.1.1.5.3.103.5.1.2;
        }

        leaf msanIPSGIpv6PortStaticBindIpAddress {
          type inet-address:InetAddressIPv6;
          description
           "Allowed IPv6 address";
          smiv2:max-access not-accessible;
          smiv2:oid 1.3.6.1.4.1.1332.1.1.5.3.103.5.1.3;
        }

        leaf msanIPSGIpv6PortStaticBindMatchedFrames {
          type yang:counter32;
          description
           "Number of matched frames for selected IPSG binding.";
          smiv2:max-access read-only;
          smiv2:oid 1.3.6.1.4.1.1332.1.1.5.3.103.5.1.4;
        }

        leaf msanIPSGIpv6PortStaticBindRowStatus {
          type snmpv2-tc:RowStatus;
          description
           "The row status object controls the creation/deletion of rows in this table.
            Its semantics are the same as those for the RowStatus textual convention specified for SNMPv2.
            For row creation use createAndGo(4).
            For row activation use active(1).
            For row deletion use destroy(6).
            
            Other values are currently not supported.";
          smiv2:max-access read-write;
          smiv2:oid 1.3.6.1.4.1.1332.1.1.5.3.103.5.1.5;
        }
      }
    }

    container msanIPSGPortBindCurrentTable {
      description
       "DThe table for storing IP source binding";
      smiv2:oid 1.3.6.1.4.1.1332.1.1.5.3.103.6;

      list msanIPSGPortBindCurrentEntry {
        key msanIPSGPortBindCurrentId;
        description
         "Description.";
        smiv2:oid 1.3.6.1.4.1.1332.1.1.5.3.103.6.1;

        leaf msanIPSGPortBindCurrentId {
          type int32;
          description
           "Table index.";
          smiv2:max-access not-accessible;
          smiv2:oid 1.3.6.1.4.1.1332.1.1.5.3.103.6.1.1;
        }

        leaf msanIPSGPortBindCurrentIfIndex {
          type if-mib:InterfaceIndex;
          description
           "Port index (ifIndex value).";
          smiv2:max-access read-only;
          smiv2:oid 1.3.6.1.4.1.1332.1.1.5.3.103.6.1.2;
        }

        leaf msanIPSGPortBindCurrentMacAddress {
          type yang:mac-address;
          description
           "Allowed MAC address";
          smiv2:max-access read-only;
          smiv2:oid 1.3.6.1.4.1.1332.1.1.5.3.103.6.1.3;
        }

        leaf msanIPSGPortBindCurrentVlanId {
          type q-bridge:VlanIndex;
          description
           "Allowed VLAN number";
          smiv2:max-access read-only;
          smiv2:oid 1.3.6.1.4.1.1332.1.1.5.3.103.6.1.4;
        }

        leaf msanIPSGPortBindCurrentIpAddressType {
          type inet-address:InetAddressType;
          description
           "Specifies the type of ip address: ipv4[1], ipv6[2].";
          smiv2:max-access read-only;
          smiv2:oid 1.3.6.1.4.1.1332.1.1.5.3.103.6.1.5;
        }

        leaf msanIPSGPortBindCurrentIpAddress {
          type inet-address:InetAddress;
          description
           "Allowed IP address";
          smiv2:max-access read-only;
          smiv2:oid 1.3.6.1.4.1.1332.1.1.5.3.103.6.1.6;
        }

        leaf msanIPSGPortBindCurrentLeaseRemainingTime {
          type yang:timeticks;
          description
           "The period for which the DHCP lease is valid.
            It is displayed in days, hours, minutes, and seconds.
            
            For static IPSG bindings this value is set to 0 (infinitive).";
          smiv2:max-access read-only;
          smiv2:oid 1.3.6.1.4.1.1332.1.1.5.3.103.6.1.7;
        }

        leaf msanIPSGPortBindCurrentType {
          type enumeration {
            enum static {
              value 1;
            }
            enum dynamic-dhcpv4 {
              value 2;
            }
            enum dynamic-dhcpv6 {
              value 3;
            }
            enum dynamic-nd {
              value 4;
            }
          }
          description
           "Type of IPSG binding.";
          smiv2:max-access read-only;
          smiv2:oid 1.3.6.1.4.1.1332.1.1.5.3.103.6.1.8;
        }

        leaf msanIPSGPortBindCurrentMatchedFrames {
          type yang:counter32;
          description
           "Number of matched frames for selected IPSG binding.";
          smiv2:max-access read-only;
          smiv2:oid 1.3.6.1.4.1.1332.1.1.5.3.103.6.1.9;
        }
      }
    }

    container msanPortVlanTable {
      status deprecated;
      description
       "Vlan config parameters per port.";
      smiv2:oid 1.3.6.1.4.1.1332.1.1.5.3.105.2;

      list msanPortVlanEntry {
        key ifIndex;
        status deprecated;
        description
         "Description.";
        smiv2:oid 1.3.6.1.4.1.1332.1.1.5.3.105.2.1;

        leaf ifIndex {
          type leafref {
            path "/if-mib:interfaces/if-mib:ifEntry/if-mib:ifIndex";
          }
        }

        leaf msanPortVlanMode {
          type enumeration {
            enum access {
              value 0;
            }
            enum trunk {
              value 1;
            }
            enum dot1qtunnel {
              value 2;
            }
            enum vlanStacking {
              value 3;
            }
          }
          status deprecated;
          description
           "Interface vlan mode.";
          smiv2:max-access read-write;
          smiv2:oid 1.3.6.1.4.1.1332.1.1.5.3.105.2.1.1;
        }

        leaf msanPortVlanStackPriority {
          type enumeration {
            enum mapPriorityFromOuterTag {
              value 0;
            }
            enum priority1 {
              value 1;
            }
            enum priority2 {
              value 2;
            }
            enum priority3 {
              value 3;
            }
            enum priority4 {
              value 4;
            }
            enum priority5 {
              value 5;
            }
            enum priority6 {
              value 6;
            }
            enum priority7 {
              value 7;
            }
          }
          status deprecated;
          description
           "Priority of inner tag when interface is in vlanStacking mode (msanPortVlanMode=vlanStacking).";
          smiv2:max-access read-write;
          smiv2:oid 1.3.6.1.4.1.1332.1.1.5.3.105.2.1.2;
        }

        leaf msanPortVlanStackVlanId {
          type int32;
          status deprecated;
          description
           "Vlan ID of inner tag when interface is in vlanStacking mode (msanPortVlanMode=vlanStacking).";
          smiv2:max-access read-write;
          smiv2:oid 1.3.6.1.4.1.1332.1.1.5.3.105.2.1.3;
        }
      }
    }

    container msanPortDVlanMapTable {
      status deprecated;
      description
       "Ingress mapping of inner VID to outer VID different from default
        (PVID) mapping.";
      smiv2:oid 1.3.6.1.4.1.1332.1.1.5.3.105.3;

      list msanPortDVlanMapEntry {
        key "ifIndex msanPortDVlanMapInTagVlanId";
        status deprecated;
        description
         "Description.";
        smiv2:oid 1.3.6.1.4.1.1332.1.1.5.3.105.3.1;

        leaf ifIndex {
          type leafref {
            path "/if-mib:interfaces/if-mib:ifEntry/if-mib:ifIndex";
          }
        }

        leaf msanPortDVlanMapInTagVlanId {
          type int32;
          status deprecated;
          description
           "Inner tag VLAN ID. DVlan functionality is used when interface is in dot1qtunnel mode.";
          smiv2:max-access not-accessible;
          smiv2:oid 1.3.6.1.4.1.1332.1.1.5.3.105.3.1.1;
        }

        leaf msanPortDVlanMapOutTagVlanId {
          type int32;
          status deprecated;
          description
           "Outer tag VLAN ID added for inner tag VLAN ID (msanPortDVlanMapInTagVlanId).
            DVlan functionality is used when interface is in dot1qtunnel mode.
            
            Value of -1 indicates that outer tag is not added for selected inner tag VLAN ID.";
          smiv2:max-access read-write;
          smiv2:oid 1.3.6.1.4.1.1332.1.1.5.3.105.3.1.2;
        }

        leaf msanPortDVlanMapRowStatus {
          type snmpv2-tc:RowStatus;
          status deprecated;
          description
           "The row status object controls the creation/deletion of rows in this table.
            For row creation use createAndWait(5) [createAndGo(4) is not supported].
            Setting this object to active(1) will activate this entry.
            Setting this object to destroy(6) will remove this entry.";
          smiv2:max-access read-write;
          smiv2:oid 1.3.6.1.4.1.1332.1.1.5.3.105.3.1.3;
        }
      }
    }

    container msanPortVlanRemarkTable {
      description
       "Vlan remarking table for ingress traffic (per port).
        
        Note: All defined Vlan remarking rules for ingress traffic  also add , automatically,
        reverse Vlan remarking rule for egress traffic on same port.";
      smiv2:oid 1.3.6.1.4.1.1332.1.1.5.3.105.4;

      list msanPortVlanRemarkEntry {
        key "ifIndex msanPortVlanRemarkSrcVlanId";
        description
         "Description.";
        smiv2:oid 1.3.6.1.4.1.1332.1.1.5.3.105.4.1;

        leaf ifIndex {
          type leafref {
            path "/if-mib:interfaces/if-mib:ifEntry/if-mib:ifIndex";
          }
        }

        leaf msanPortVlanRemarkSrcVlanId {
          type int32 {
            range "1..4094";
          }
          description
           "Ingress traffic Source VLAN ID which will be changed to Destination VLAN ID
            (msanPortVlanRemarkDstVlanId) by VLAN remarking rule.";
          smiv2:max-access read-write;
          smiv2:oid 1.3.6.1.4.1.1332.1.1.5.3.105.4.1.1;
        }

        leaf msanPortVlanRemarkDstVlanId {
          type int32 {
            range "1..4094";
          }
          description
           "Destination VLAN ID to which will be changed Source VLAN ID of ingress traffic (msanPortVlanRemarkSrcVlanId)
            by VLAN remarking rule.";
          smiv2:max-access read-write;
          smiv2:oid 1.3.6.1.4.1.1332.1.1.5.3.105.4.1.2;
        }

        leaf msanPortVlanRemarkRowStatus {
          type snmpv2-tc:RowStatus;
          description
           "The row status object controls the creation/deletion of rows in this table.
            Its semantics are the same as those for the RowStatus textual convention specified for SNMPv2.
            For row creation use createAndWait(5).
            For row activation use active(1).
            For row deletion use destroy(6).
            
            Other values are currently not supported.
            
            For row activation next terms must be accomplished:
            - msanPortVlanRemarkDstVlanId must be defined (default value not defined)
            
            Note: All defined Vlan remarking rules for ingress traffic  also add , automatically,
            reverse Vlan remarking rule for egress traffic on same port.";
          smiv2:max-access read-write;
          smiv2:oid 1.3.6.1.4.1.1332.1.1.5.3.105.4.1.3;
        }
      }
    }

    container msanPortDVlanTable {
      description
       "Description.";
      smiv2:oid 1.3.6.1.4.1.1332.1.1.5.3.105.5;

      list msanPortDVlanEntry {
        key ifIndex;
        description
         "Description.";
        smiv2:oid 1.3.6.1.4.1.1332.1.1.5.3.105.5.1;

        leaf ifIndex {
          type leafref {
            path "/if-mib:interfaces/if-mib:ifEntry/if-mib:ifIndex";
          }
        }

        leaf msanPortDVlanTagMode {
          type enumeration {
            enum enable {
              value 1;
            }
            enum disable {
              value 2;
            }
          }
          description
           "Administrative state of 802.1Q tunneling (DVLAN) mode.";
          smiv2:defval disable;
          smiv2:max-access read-write;
          smiv2:oid 1.3.6.1.4.1.1332.1.1.5.3.105.5.1.1;
        }

        leaf msanPortDVlanStackVlanId {
          type int32;
          description
           "Vlan ID of inner tag when interface is in vlanStacking mode.
            
            Interface is in vlanStacking mode when msanPortDVlanTagMode=enable and
            msanPortDVlanStackVlanId>=0.
            
            msanPortDVlanStackVlanId value of -1 indicates that vlanStacking mode is not activated.";
          smiv2:max-access read-write;
          smiv2:oid 1.3.6.1.4.1.1332.1.1.5.3.105.5.1.2;
        }

        leaf msanPortDVlanStackPriority {
          type enumeration {
            enum priority0 {
              value 0;
            }
            enum priority1 {
              value 1;
            }
            enum priority2 {
              value 2;
            }
            enum priority3 {
              value 3;
            }
            enum priority4 {
              value 4;
            }
            enum priority5 {
              value 5;
            }
            enum priority6 {
              value 6;
            }
            enum priority7 {
              value 7;
            }
          }
          description
           "Priority of inner tag when interface is in vlanStacking mode.
            
            Interface is in vlanStacking mode when msanPortDVlanTagMode=enable and
            msanPortDVlanStackVlanId>=0.";
          smiv2:defval priority0;
          smiv2:max-access read-write;
          smiv2:oid 1.3.6.1.4.1.1332.1.1.5.3.105.5.1.3;
        }
      }
    }

    container msanPortDVlanConfigTable {
      description
       "Ingress mapping of inner VID to outer VID different from default
        (PVID) mapping.";
      smiv2:oid 1.3.6.1.4.1.1332.1.1.5.3.105.6;

      list msanPortDVlanConfigEntry {
        key "ifIndex msanDVlanConfigInTagVlanId msanDVlanConfigInTagPriority";
        description
         "Description.";
        smiv2:oid 1.3.6.1.4.1.1332.1.1.5.3.105.6.1;

        leaf ifIndex {
          type leafref {
            path "/if-mib:interfaces/if-mib:ifEntry/if-mib:ifIndex";
          }
        }

        leaf msanDVlanConfigInTagVlanId {
          type int32;
          description
           "Inner tag VLAN ID. DVlan functionality is used when interface is in dot1qtunnel mode.";
          smiv2:max-access not-accessible;
          smiv2:oid 1.3.6.1.4.1.1332.1.1.5.3.105.6.1.1;
        }

        leaf msanDVlanConfigInTagPriority {
          type enumeration {
            enum priority0 {
              value 0;
            }
            enum priority1 {
              value 1;
            }
            enum priority2 {
              value 2;
            }
            enum priority3 {
              value 3;
            }
            enum priority4 {
              value 4;
            }
            enum priority5 {
              value 5;
            }
            enum priority6 {
              value 6;
            }
            enum priority7 {
              value 7;
            }
            enum unspecified {
              value 8;
            }
          }
          description
           "Priority of inner tag.
            Value unspecified(8) defines that rule line applies to all packets with
            appropriate msanDVlanConfigInTagVlanId, except if packet match to other more specific rule.";
          smiv2:max-access not-accessible;
          smiv2:oid 1.3.6.1.4.1.1332.1.1.5.3.105.6.1.2;
        }

        leaf msanDVlanConfigOutTagVlanId {
          type int32;
          description
           "Outer tag VLAN ID added for inner tag VLAN ID (msanPortDVlanConfigInTagVlanId).
            DVlan functionality is used when interface is in dot1qtunnel mode.
            
            Value of -1 indicates that outer tag is not added for selected inner tag VLAN ID.";
          smiv2:max-access read-write;
          smiv2:oid 1.3.6.1.4.1.1332.1.1.5.3.105.6.1.3;
        }

        leaf msanDVlanConfigOutTagPriority {
          type enumeration {
            enum priority0 {
              value 0;
            }
            enum priority1 {
              value 1;
            }
            enum priority2 {
              value 2;
            }
            enum priority3 {
              value 3;
            }
            enum priority4 {
              value 4;
            }
            enum priority5 {
              value 5;
            }
            enum priority6 {
              value 6;
            }
            enum priority7 {
              value 7;
            }
            enum unspecified {
              value 8;
            }
          }
          description
           "Priority of outer tag.
            Value unspecified(8) defines that msanDVlanMapInTagPriority is copied to outer tag.";
          smiv2:defval priority0;
          smiv2:max-access read-write;
          smiv2:oid 1.3.6.1.4.1.1332.1.1.5.3.105.6.1.4;
        }

        leaf msanDVlanConfigRowStatus {
          type snmpv2-tc:RowStatus;
          description
           "The row status object controls the creation/deletion of rows in this table.
            For row creation use createAndWait(5) [createAndGo(4) is not supported].
            Setting this object to active(1) will activate this entry.
            Setting this object to destroy(6) will remove this entry.";
          smiv2:max-access read-write;
          smiv2:oid 1.3.6.1.4.1.1332.1.1.5.3.105.6.1.5;
        }
      }
    }

    container msanPortVlanRemarkAdminTable {
      description
       "Description.";
      smiv2:oid 1.3.6.1.4.1.1332.1.1.5.3.105.7;

      list msanPortVlanRemarkAdminEntry {
        key ifIndex;
        description
         "Description.";
        smiv2:oid 1.3.6.1.4.1.1332.1.1.5.3.105.7.1;

        leaf ifIndex {
          type leafref {
            path "/if-mib:interfaces/if-mib:ifEntry/if-mib:ifIndex";
          }
        }

        leaf msanPortVlanRemarkAdminMode {
          type enumeration {
            enum enable {
              value 1;
            }
            enum disable {
              value 2;
            }
          }
          description
           "Administrative mode for VLAN Remarking";
          smiv2:max-access read-write;
          smiv2:oid 1.3.6.1.4.1.1332.1.1.5.3.105.7.1.1;
        }
      }
    }

   container msanUplinkPortVlanTable {
      description
       "Description.";
      smiv2:oid 1.3.6.1.4.1.1332.1.1.5.3.105.8;

      list msanUplinkPortVlanEntry {

        key "msanUplinkPortVlanIfName msanUplinkPortVlanId";
        description
         "Description.";
        smiv2:oid 1.3.6.1.4.1.1332.1.1.5.3.105.8.1;

        leaf msanUplinkPortVlanIfName {
          type if:interface-state-ref;
          description
           "Index of ONU (from ifTable).";
          smiv2:max-access not-accessible;
          smiv2:oid 1.3.6.1.4.1.1332.1.1.5.3.111.10.1.1;
        }

        leaf msanUplinkPortVlanId {
          type int32 {
            range "0..4094";
          }
          description
           "Vlan ID.";
          smiv2:max-access read-write;
          smiv2:oid 1.3.6.1.4.1.1332.1.1.5.3.105.8.1.1;
        }

        leaf msanUplinkPortVlanMode {
          type enumeration {
            enum tagged {
              value 1;
            }
            enum native {
              value 2;
            }
            enum unconfigured {
              value 3;
            }
          }
          description
           "Vlan Mode.";
          smiv2:max-access read-write;
          smiv2:oid 1.3.6.1.4.1.1332.1.1.5.3.105.8.1.2;
        }

        leaf msanUplinkPortVlanMulticastMode {
          type enumeration {
            enum discarding {
              value 1;
            }
            enum flooding {
              value 2;
            }
            enum snooping {
              value 3;
            }
            enum snoopingAndFloodUnknown {
              value 4;
            }
            enum undefined {
              value 5;
            }
          }
          description
           "Vlan Multicast Mode.
            This parameter can't be set if msanUplinkPortVlanMulticastMode=unconfigured(3)";
          smiv2:defval undefined;
          smiv2:max-access read-write;
          smiv2:oid 1.3.6.1.4.1.1332.1.1.5.3.105.8.1.3;
        }
      }
    }

    container msanPortAtmPvcTable {
      description
       "Description.";
      smiv2:oid 1.3.6.1.4.1.1332.1.1.5.3.106.2;

      list msanPortAtmPvcEntry {
        key "ifIndex msanPortAtmPvcVpi msanPortAtmPvcVci";
        description
         "Description.";
        smiv2:oid 1.3.6.1.4.1.1332.1.1.5.3.106.2.1;

        leaf ifIndex {
          type leafref {
            path "/if-mib:interfaces/if-mib:ifEntry/if-mib:ifIndex";
          }
        }

        leaf msanPortAtmPvcVpi {
          type int32 {
            range "0..255";
          }
          description
           "ATM-PVC(Permanent Virtual Circuits) VPI(Virtual Path Identifier) value.";
          smiv2:max-access not-accessible;
          smiv2:oid 1.3.6.1.4.1.1332.1.1.5.3.106.2.1.1;
        }

        leaf msanPortAtmPvcVci {
          type int32 {
            range "32..255";
          }
          description
           "ATM-PVC(Permanent Virtual Circuits) VCI(Virtual Channel Identifier) value.";
          smiv2:max-access not-accessible;
          smiv2:oid 1.3.6.1.4.1.1332.1.1.5.3.106.2.1.2;
        }

        leaf msanPortAtmPvcPvid {
          type int32 {
            range "0..4094";
          }
          description
           "The PVID, the VLAN ID assigned to untagged frames or
            Priority-Tagged frames received on this ATM-PVC(Permanent Virtual Circuits).
            
            Value 0 defines that PVID is not set.";
          smiv2:defval 0;
          smiv2:max-access read-write;
          smiv2:oid 1.3.6.1.4.1.1332.1.1.5.3.106.2.1.3;
        }

        leaf msanPortAtmPvcRowStatus {
          type snmpv2-tc:RowStatus;
          description
           "The row status object controls the creation/deletion of rows in this table.
            For row creation use createAndWait(5) [createAndGo(4) is not supported].
            Setting this object to active(1) will activate this entry.
            Setting this object to destroy(6) will remove this entry.";
          smiv2:max-access read-write;
          smiv2:oid 1.3.6.1.4.1.1332.1.1.5.3.106.2.1.4;
        }
      }
    }

    container msanEnergyMeterEnergyTable {
      description
       "Energy values.";
      smiv2:oid 1.3.6.1.4.1.1332.1.1.5.3.107.2;

      list msanEnergyMeterEnergyEntry {
        key "msanEnergyMeterTariff msanEnergyMeterDepth";
        description
         "Description.";
        smiv2:oid 1.3.6.1.4.1.1332.1.1.5.3.107.2.1;

        leaf msanEnergyMeterTariff {
          type uint32 {
            range "1..8";
          }
          description
           "This is msanEnergyMeterTariff index in msanEnergyMeterEnergyTable
            Defines tariff. 1 � tariff No1, 1 � tariff No2, �, 8 - tariff No8";
          smiv2:max-access not-accessible;
          smiv2:oid 1.3.6.1.4.1.1332.1.1.5.3.107.2.1.1;
        }

        leaf msanEnergyMeterDepth {
          type uint32 {
            range "1..13";
          }
          description
           "This is msanEnergyMeterDepth index in msanEnergyMeterEnergyTable.
            Defines time span.
            1 � current value,
            2 � value at the end of previous month,
            3 � value at the end of 2. month ago, �, 13 �value at the end of the 12. month ago";
          smiv2:max-access not-accessible;
          smiv2:oid 1.3.6.1.4.1.1332.1.1.5.3.107.2.1.2;
        }

        leaf msanEnergyMeterEnergyValue {
          type uint32;
          units "0.01 kWh";
          description
           "Energy value.";
          smiv2:max-access read-only;
          smiv2:oid 1.3.6.1.4.1.1332.1.1.5.3.107.2.1.3;
        }
      }
    }

    container msanEnergyMeterEnergySumTable {
      description
       "Energy sum values of all tariffs.";
      smiv2:oid 1.3.6.1.4.1.1332.1.1.5.3.107.3;

      list msanEnergyMeterEnergySumEntry {
        key msanEnergyMeterDepth;
        description
         "Description.";
        smiv2:oid 1.3.6.1.4.1.1332.1.1.5.3.107.3.1;

        leaf msanEnergyMeterDepth {
          type leafref {
            path "/iskratel-msan:ISKRATEL-MSAN-MIB/iskratel-msan:msanEnergyMeterEnergyTable/iskratel-msan:msanEnergyMeterEnergyEntry/iskratel-msan:msanEnergyMeterDepth";
          }
        }

        leaf msanEnergyMeterEnergySumValue {
          type uint32;
          units "0.01 kWh";
          description
           "Energy sum value of all tariffs";
          smiv2:max-access read-only;
          smiv2:oid 1.3.6.1.4.1.1332.1.1.5.3.107.3.1.1;
        }
      }
    }

    container msanArpInspectionPortTable {
      description
       "Arp Inspection.";
      smiv2:oid 1.3.6.1.4.1.1332.1.1.5.3.108.2;

      list msanArpInspectionPortEntry {
        key ifIndex;
        description
         "Description.";
        smiv2:oid 1.3.6.1.4.1.1332.1.1.5.3.108.2.1;

        leaf ifIndex {
          type leafref {
            path "/if-mib:interfaces/if-mib:ifEntry/if-mib:ifIndex";
          }
        }

        leaf msanArpInspectionPortAdminMode {
          type enumeration {
            enum enable {
              value 1;
            }
            enum disable {
              value 2;
            }
          }
          description
           "Enable/disable dynamic arp inspection for the selected interface.";
          smiv2:defval disable;
          smiv2:max-access read-write;
          smiv2:oid 1.3.6.1.4.1.1332.1.1.5.3.108.2.1.1;
        }

        leaf msanArpInspectionPortStatDroppedFrames {
          type int32;
          description
           "Number of discarded ARP packets on interface.";
          smiv2:max-access read-only;
          smiv2:oid 1.3.6.1.4.1.1332.1.1.5.3.108.2.1.2;
        }
      }
    }

    container msanArpInspectionVlanTable {
      description
       "Arp Inspection.";
      smiv2:oid 1.3.6.1.4.1.1332.1.1.5.3.108.3;

      list msanArpInspectionVlanEntry {
        key dot1qVlanIndex;
        description
         "Description.";
        smiv2:oid 1.3.6.1.4.1.1332.1.1.5.3.108.3.1;

        leaf dot1qVlanIndex {
          type leafref {
            path "/q-bridge:Q-BRIDGE-MIB/q-bridge:dot1qVlanCurrentTable/q-bridge:dot1qVlanCurrentEntry/q-bridge:dot1qVlanIndex";
          }
        }

        leaf msanArpInspectionVlanAdminMode {
          type enumeration {
            enum enable {
              value 1;
            }
            enum disable {
              value 2;
            }
          }
          description
           "Enable/disable dynamic arp inspection per vlan.";
          smiv2:defval disable;
          smiv2:max-access read-write;
          smiv2:oid 1.3.6.1.4.1.1332.1.1.5.3.108.3.1.1;
        }

        leaf msanArpInspectionVlanStatDroppedFrames {
          type int32;
          description
           "Number of discarded ARP packets per vlan.";
          smiv2:max-access read-only;
          smiv2:oid 1.3.6.1.4.1.1332.1.1.5.3.108.3.1.2;
        }
      }
    }

    container msanIsaPortStatTable {
      description
       "Description.";
      smiv2:oid 1.3.6.1.4.1.1332.1.1.5.3.109.2.1;

      list msanIsaPortStatEntry {
        key ifIndex;
        description
         "Description.";
        smiv2:oid 1.3.6.1.4.1.1332.1.1.5.3.109.2.1.1;

        leaf ifIndex {
          type leafref {
            path "/if-mib:interfaces/if-mib:ifEntry/if-mib:ifIndex";
          }
        }

        leaf msanIsaPortStatTalMatchedFrames {
          type yang:counter32;
          description
           "Number of TAL matched frames.";
          smiv2:max-access read-only;
          smiv2:oid 1.3.6.1.4.1.1332.1.1.5.3.109.2.1.1.1;
        }

        leaf msanIsaPortStatTalDroppedFrames {
          type yang:counter32;
          description
           "Number of TAL dropped frames.";
          smiv2:max-access read-only;
          smiv2:oid 1.3.6.1.4.1.1332.1.1.5.3.109.2.1.1.2;
        }

        leaf msanIsaPortStatAuthenReqSent {
          type yang:counter32;
          description
           "Number of sent Authentication requests.";
          smiv2:max-access read-only;
          smiv2:oid 1.3.6.1.4.1.1332.1.1.5.3.109.2.1.1.3;
        }

        leaf msanIsaPortStatAuthenReqConfirmed {
          type yang:counter32;
          description
           "Number of confirmed Authentication requests.";
          smiv2:max-access read-only;
          smiv2:oid 1.3.6.1.4.1.1332.1.1.5.3.109.2.1.1.4;
        }

        leaf msanIsaPortStatAuthenReqRejected {
          type yang:counter32;
          description
           "Number of rejected Authentication requests.";
          smiv2:max-access read-only;
          smiv2:oid 1.3.6.1.4.1.1332.1.1.5.3.109.2.1.1.6;
        }

        leaf msanIsaPortStatAuthenTimeoutExpired {
          type yang:counter32;
          description
           "Number of expired Authentication timeouts.";
          smiv2:max-access read-only;
          smiv2:oid 1.3.6.1.4.1.1332.1.1.5.3.109.2.1.1.7;
        }

        leaf msanIsaPortStatAuthorReqSent {
          type yang:counter32;
          description
           "Number of sent Authorization requests.";
          smiv2:max-access read-only;
          smiv2:oid 1.3.6.1.4.1.1332.1.1.5.3.109.2.1.1.8;
        }

        leaf msanIsaPortStatAuthorReqConfirmed {
          type yang:counter32;
          description
           "Number of confirmed Authorization requests.";
          smiv2:max-access read-only;
          smiv2:oid 1.3.6.1.4.1.1332.1.1.5.3.109.2.1.1.9;
        }

        leaf msanIsaPortStatAuthorReqRejected {
          type yang:counter32;
          description
           "Number of rejected Authorization requests.";
          smiv2:max-access read-only;
          smiv2:oid 1.3.6.1.4.1.1332.1.1.5.3.109.2.1.1.10;
        }

        leaf msanIsaPortStatAuthorTimeoutExpired {
          type yang:counter32;
          description
           "Number of expired Authorization timeouts.";
          smiv2:max-access read-only;
          smiv2:oid 1.3.6.1.4.1.1332.1.1.5.3.109.2.1.1.11;
        }
      }
    }

    container msanIsaRadiusServerTable {
      description
       "Description.";
      smiv2:oid 1.3.6.1.4.1.1332.1.1.5.3.109.3;

      list msanIsaRadiusServerEntry {
        key "msanIsaRadiusServerIpAddress msanIsaRadiusServerType";
        description
         "Description.";
        smiv2:oid 1.3.6.1.4.1.1332.1.1.5.3.109.3.1;

        leaf msanIsaRadiusServerIpAddress {
          type inet:ipv4-address;
          description
           "ISA Radius server IP address.";
          smiv2:max-access not-accessible;
          smiv2:oid 1.3.6.1.4.1.1332.1.1.5.3.109.3.1.1;
        }

        leaf msanIsaRadiusServerType {
          type enumeration {
            enum authentication {
              value 1;
            }
            enum accounting {
              value 2;
            }
          }
          description
           "ISA Radius server type.";
          smiv2:max-access not-accessible;
          smiv2:oid 1.3.6.1.4.1.1332.1.1.5.3.109.3.1.2;
        }

        leaf msanIsaRadiusServerPort {
          type uint32 {
            range "0..65535";
          }
          description
           " ISA Radius server port number.
            
            If msanIsaRadiusServerType = authentication(1) then default port value is 1812.
            If msanIsaRadiusServerType = accounting(2) then default port value is 1813.";
          smiv2:max-access read-write;
          smiv2:oid 1.3.6.1.4.1.1332.1.1.5.3.109.3.1.3;
        }

        leaf msanIsaRadiusServerSecret {
          type rfc1213-mib:DisplayString {
            length "0..16";
          }
          description
           "ISA Radius server shared secret.";
          smiv2:defval "";
          smiv2:max-access read-write;
          smiv2:oid 1.3.6.1.4.1.1332.1.1.5.3.109.3.1.4;
        }

        leaf msanIsaRadiusServerPrimaryMode {
          type enumeration {
            enum primary {
              value 1;
            }
            enum secondary {
              value 2;
            }
          }
          description
           "ISA Radius server primary mode.
            Only one server can be defined as primary(1).";
          smiv2:max-access read-write;
          smiv2:oid 1.3.6.1.4.1.1332.1.1.5.3.109.3.1.5;
        }

        leaf msanIsaRadiusServerRowStatus {
          type snmpv2-tc:RowStatus;
          description
           "The row status object controls the creation/deletion of rows in this table.
            Its semantics are the same as those for the RowStatus textual convention specified for SNMPv2.
            For row creation use createAndWait(5).
            For row activation use active(1).
            For row deletion use destroy(6).
            
            Other values are currently not supported.
            
            For row activation parameter msanIsaRadiusServerType must be defined.";
          smiv2:max-access read-write;
          smiv2:oid 1.3.6.1.4.1.1332.1.1.5.3.109.3.1.6;
        }
      }
    }

    container msanIsaPortTable {
      description
       "Description.";
      smiv2:oid 1.3.6.1.4.1.1332.1.1.5.3.109.5;

      list msanIsaPortEntry {
        key ifIndex;
        description
         "Description.";
        smiv2:oid 1.3.6.1.4.1.1332.1.1.5.3.109.5.1;

        leaf ifIndex {
          type leafref {
            path "/if-mib:interfaces/if-mib:ifEntry/if-mib:ifIndex";
          }
        }

        leaf msanIsaPortTalAdminMode {
          type enumeration {
            enum enable {
              value 1;
            }
            enum disable {
              value 2;
            }
          }
          description
           "ISA TAL functionality admin mode.";
          smiv2:defval disable;
          smiv2:max-access read-write;
          smiv2:oid 1.3.6.1.4.1.1332.1.1.5.3.109.5.1.1;
        }

        leaf msanIsaPortAuthentication {
          type enumeration {
            enum enable {
              value 1;
            }
            enum disable {
              value 2;
            }
          }
          description
           "ISA Authentication administrative state.";
          smiv2:defval enable;
          smiv2:max-access read-write;
          smiv2:oid 1.3.6.1.4.1.1332.1.1.5.3.109.5.1.2;
        }

        leaf msanIsaPortAuthorization {
          type enumeration {
            enum enable {
              value 1;
            }
            enum disable {
              value 2;
            }
          }
          description
           "ISA Authorization administrative state.";
          smiv2:defval enable;
          smiv2:max-access read-write;
          smiv2:oid 1.3.6.1.4.1.1332.1.1.5.3.109.5.1.3;
        }

        leaf msanIsaPortAccounting {
          type enumeration {
            enum enable {
              value 1;
            }
            enum disable {
              value 2;
            }
          }
          description
           "ISA Accounting administrative state.";
          smiv2:defval disable;
          smiv2:max-access read-write;
          smiv2:oid 1.3.6.1.4.1.1332.1.1.5.3.109.5.1.4;
        }

        leaf msanIsaPortLoginMask {
          type bits {
            bit circuitId {
              position 0;
            }
            bit remoteId {
              position 1;
            }
            bit vendorId {
              position 2;
            }
            bit clientId {
              position 3;
            }
            bit sourceMAC {
              position 4;
            }
            bit sourceIP {
              position 5;
            }
            bit userPattern {
              position 6;
            }
          }
          description
           "ISA login mask.";
          smiv2:defval "{circuitId}";
          smiv2:max-access read-write;
          smiv2:oid 1.3.6.1.4.1.1332.1.1.5.3.109.5.1.5;
        }

        leaf msanIsaPortLoginUserPatternMask {
          type binary {
            length "0..128";
          }
          description
           "This mask value identifies the portion of input packet that
            is send to Radius server, if userPattern bit is set in msanIsaPortLoginMask.
            Empty string indicates that parameter has not been defined.";
          smiv2:max-access read-write;
          smiv2:oid 1.3.6.1.4.1.1332.1.1.5.3.109.5.1.6;
        }

        leaf msanIsaPortTalAutomaticReq {
          type enumeration {
            enum enable {
              value 1;
            }
            enum disable {
              value 2;
            }
          }
          description
           "TAL automatic request state.";
          smiv2:defval disable;
          smiv2:max-access read-write;
          smiv2:oid 1.3.6.1.4.1.1332.1.1.5.3.109.5.1.7;
        }
      }
    }

    container msanIsaTalPortMatchTable {
      description
       "Description.";
      smiv2:oid 1.3.6.1.4.1.1332.1.1.5.3.109.6;

      list msanIsaTalPortMatchEntry {
        key ifIndex;
        description
         "Description.";
        smiv2:oid 1.3.6.1.4.1.1332.1.1.5.3.109.6.1;

        leaf ifIndex {
          type leafref {
            path "/if-mib:interfaces/if-mib:ifEntry/if-mib:ifIndex";
          }
        }

        leaf msanIsaTalPortMatchEthertype {
          type int32 {
            range "-1..65535";
          }
          description
           "Match incoming packet frame with specified EtherType value.
            A value of -1 indicates that parameter has not been defined.";
          smiv2:defval -1;
          smiv2:max-access read-write;
          smiv2:oid 1.3.6.1.4.1.1332.1.1.5.3.109.6.1.1;
        }

        leaf msanIsaTalPortMatchMacSrcAddr {
          type yang:mac-address;
          description
           "Match incoming  packet frame with specified Source MAC address.
            Empty string indicates that parameter has not been defined.";
          smiv2:defval "";
          smiv2:max-access read-write;
          smiv2:oid 1.3.6.1.4.1.1332.1.1.5.3.109.6.1.2;
        }

        leaf msanIsaTalPortMatchMacSrcMask {
          type yang:mac-address;
          description
           "This mask value identifies the portion of msanIsaTalPortMatchMacSrcAddr that
            is compared with input packet.
            Empty string indicates that parameter has not been defined";
          smiv2:defval "";
          smiv2:max-access read-write;
          smiv2:oid 1.3.6.1.4.1.1332.1.1.5.3.109.6.1.3;
        }

        leaf msanIsaTalPortMatchVlanId {
          type int32 {
            range "-1..4094";
          }
          description
           "Match incoming packet frame with specified VLAN ID value (1-4094).
            A value of -1 indicates that parameter has not been defined";
          smiv2:max-access read-write;
          smiv2:oid 1.3.6.1.4.1.1332.1.1.5.3.109.6.1.4;
        }

        leaf msanIsaTalPortMatchIpSrcAddr {
          type inet:ipv4-address;
          description
           "Match incoming packet frame with specified source IP address.
            Empty string indicates that parameter has not been defined.";
          smiv2:defval "";
          smiv2:max-access read-write;
          smiv2:oid 1.3.6.1.4.1.1332.1.1.5.3.109.6.1.5;
        }

        leaf msanIsaTalPortMatchIpSrcMask {
          type inet:ipv4-address;
          description
           "This mask value identifies the portion of msanIsaTalPortMatchIpSrcAddr that
            is compared with input packet.
            Empty string indicates that parameter has not been defined";
          smiv2:defval "";
          smiv2:max-access read-write;
          smiv2:oid 1.3.6.1.4.1.1332.1.1.5.3.109.6.1.6;
        }

        leaf msanIsaTalPortMatchDhcpType {
          type enumeration {
            enum undefined {
              value 0;
            }
            enum discover {
              value 1;
            }
            enum request {
              value 2;
            }
          }
          description
           "Match incoming  packet frame with specified DHCP type value.";
          smiv2:defval undefined;
          smiv2:max-access read-write;
          smiv2:oid 1.3.6.1.4.1.1332.1.1.5.3.109.6.1.7;
        }

        leaf msanIsaTalPortMatchDhcpOpt60VendorId {
          type rfc1213-mib:DisplayString;
          description
           "Match incoming packet frame with specified DHCP option 60 vendorId value.
            Empty string indicates that parameter has not been defined.";
          smiv2:defval "";
          smiv2:max-access read-write;
          smiv2:oid 1.3.6.1.4.1.1332.1.1.5.3.109.6.1.8;
        }

        leaf msanIsaTalPortMatchDhcpOpt61ClientId {
          type rfc1213-mib:DisplayString;
          description
           "Match incoming  packet frame with specified DHCP option 61 clientId value.
            Empty string indicates that parameter has not been defined.";
          smiv2:defval "";
          smiv2:max-access read-write;
          smiv2:oid 1.3.6.1.4.1.1332.1.1.5.3.109.6.1.9;
        }

        leaf msanIsaTalPortMatchDhcpOpt61ClientIdMacAddr {
          type yang:mac-address;
          description
           "Match incoming packet frame with specified DHCP option 61 MAC address.
            Empty string indicates that parameter has not been defined.";
          smiv2:defval "";
          smiv2:max-access read-write;
          smiv2:oid 1.3.6.1.4.1.1332.1.1.5.3.109.6.1.10;
        }

        leaf msanIsaTalPortMatchDhcpOpt82RemoteId {
          type rfc1213-mib:DisplayString;
          description
           "Match incoming  packet frame with specified DHCP option 82 remoteId value.
            Empty string indicates that parameter has not been defined.";
          smiv2:defval "";
          smiv2:max-access read-write;
          smiv2:oid 1.3.6.1.4.1.1332.1.1.5.3.109.6.1.11;
        }

        leaf msanIsaTalPortMatchUserBits {
          type binary {
            length "0..128";
          }
          description
           "Match incoming  packet frame with specified user defined bits.
            Empty string indicates that parameter has not been defined.";
          smiv2:defval "";
          smiv2:max-access read-write;
          smiv2:oid 1.3.6.1.4.1.1332.1.1.5.3.109.6.1.12;
        }

        leaf msanIsaTalPortMatchUserMask {
          type binary {
            length "0..128";
          }
          description
           "This mask value identifies the portion of msanIsaTalPortMatchUserBits that
            is compared with input packet.
            Empty string indicates that parameter has not been defined.";
          smiv2:defval "";
          smiv2:max-access read-write;
          smiv2:oid 1.3.6.1.4.1.1332.1.1.5.3.109.6.1.13;
        }
      }
    }

    container msanIsaTalPatternMatchTable {
      description
       "This table is used to store the pattern match name, pattern
        rules and the corresponding login mask for the pattern match.";
      smiv2:oid 1.3.6.1.4.1.1332.1.1.5.3.109.7;

      list msanIsaTalPatternMatchEntry {
        key msanIsaTalPatternMatchName;
        description
         "Each entry in this table contains the
          a unique pattern match along with the loginmask to identify the user login packets.";
        smiv2:oid 1.3.6.1.4.1.1332.1.1.5.3.109.7.1;

        leaf msanIsaTalPatternMatchName {
          type binary {
            length "1..64";
          }
          description
           "Pattern match name.";
          smiv2:max-access not-accessible;
          smiv2:oid 1.3.6.1.4.1.1332.1.1.5.3.109.7.1.1;
        }

        leaf msanIsaTalPatternMatchEthertype {
          type int32 {
            range "-1..65535";
          }
          description
           "Match incoming packet frame with specified EtherType value.
            A value of -1 indicates that parameter has not been defined.";
          smiv2:defval -1;
          smiv2:max-access read-write;
          smiv2:oid 1.3.6.1.4.1.1332.1.1.5.3.109.7.1.2;
        }

        leaf msanIsaTalPatternMatchMacSrcAddr {
          type yang:mac-address;
          description
           "Match incoming  packet frame with specified Source MAC address.
            Empty string indicates that parameter has not been defined.";
          smiv2:defval "";
          smiv2:max-access read-write;
          smiv2:oid 1.3.6.1.4.1.1332.1.1.5.3.109.7.1.3;
        }

        leaf msanIsaTalPatternMatchMacSrcMask {
          type yang:mac-address;
          description
           "This mask value identifies the portion of
            msanIsaTalPatternMatchMacSrcAddr that is compared with input
            packet. Empty string indicates that parameter has not been
            defined";
          smiv2:defval "";
          smiv2:max-access read-write;
          smiv2:oid 1.3.6.1.4.1.1332.1.1.5.3.109.7.1.4;
        }

        leaf msanIsaTalPatternMatchVlanId {
          type int32 {
            range "-1..4094";
          }
          description
           "Match incoming packet frame with specified VLAN ID value
            (1-4094). A value of -1 indicates that parameter has not been
            defined";
          smiv2:max-access read-write;
          smiv2:oid 1.3.6.1.4.1.1332.1.1.5.3.109.7.1.5;
        }

        leaf msanIsaTalPatternMatchIpSrcAddr {
          type inet:ipv4-address;
          description
           "Match incoming packet frame with specified source IP address.
            Empty string indicates that parameter has not been defined.";
          smiv2:defval "";
          smiv2:max-access read-write;
          smiv2:oid 1.3.6.1.4.1.1332.1.1.5.3.109.7.1.6;
        }

        leaf msanIsaTalPatternMatchIpSrcMask {
          type inet:ipv4-address;
          description
           "This mask value identifies the portion of
            msanIsaTalPatternMatchIpSrcAddr that is compared with input
            packet.	Empty string indicates that parameter has not been
            defined";
          smiv2:defval "";
          smiv2:max-access read-write;
          smiv2:oid 1.3.6.1.4.1.1332.1.1.5.3.109.7.1.7;
        }

        leaf msanIsaTalPatternMatchDhcpType {
          type enumeration {
            enum undefined {
              value 0;
            }
            enum discover {
              value 1;
            }
            enum request {
              value 2;
            }
          }
          description
           "Match incoming  packet frame with specified DHCP type value.";
          smiv2:defval undefined;
          smiv2:max-access read-write;
          smiv2:oid 1.3.6.1.4.1.1332.1.1.5.3.109.7.1.8;
        }

        leaf msanIsaTalPatternMatchDhcpOpt60VendorId {
          type rfc1213-mib:DisplayString;
          description
           "Match incoming packet frame with specified DHCP option 60
            vendorId value.	Empty string indicates that parameter has not
            been defined.";
          smiv2:defval "";
          smiv2:max-access read-write;
          smiv2:oid 1.3.6.1.4.1.1332.1.1.5.3.109.7.1.9;
        }

        leaf msanIsaTalPatternMatchDhcpOpt61ClientId {
          type rfc1213-mib:DisplayString;
          description
           "Match incoming  packet frame with specified DHCP option 61
            clientId value.	Empty string indicates that parameter has not
            been defined.";
          smiv2:defval "";
          smiv2:max-access read-write;
          smiv2:oid 1.3.6.1.4.1.1332.1.1.5.3.109.7.1.10;
        }

        leaf msanIsaTalPatternMatchDhcpOpt61ClientIdMacAddr {
          type yang:mac-address;
          description
           "Match incoming packet frame with specified DHCP option 61 MAC
            address. Empty string indicates that parameter has not been
            defined.";
          smiv2:defval "";
          smiv2:max-access read-write;
          smiv2:oid 1.3.6.1.4.1.1332.1.1.5.3.109.7.1.11;
        }

        leaf msanIsaTalPatternMatchDhcpOpt82RemoteId {
          type rfc1213-mib:DisplayString;
          description
           "Match incoming  packet frame with specified DHCP option 82
            remoteId value.	Empty string indicates that parameter has not
            been defined.";
          smiv2:defval "";
          smiv2:max-access read-write;
          smiv2:oid 1.3.6.1.4.1.1332.1.1.5.3.109.7.1.12;
        }

        leaf msanIsaTalPatternMatchUserBits {
          type binary {
            length "0..128";
          }
          description
           "Match incoming  packet frame with specified user defined bits.
            Empty string indicates that parameter has not been defined.";
          smiv2:defval "";
          smiv2:max-access read-write;
          smiv2:oid 1.3.6.1.4.1.1332.1.1.5.3.109.7.1.13;
        }

        leaf msanIsaTalPatternMatchUserMask {
          type binary {
            length "0..128";
          }
          description
           "This mask value identifies the portion of
            msanIsaTalPatternMatchUserBits that is compared with input
            packet. Empty string indicates that parameter has not been
            defined.";
          smiv2:defval "";
          smiv2:max-access read-write;
          smiv2:oid 1.3.6.1.4.1.1332.1.1.5.3.109.7.1.14;
        }

        leaf msanIsaTalPatternMatchLoginMask {
          type bits {
            bit circuitId {
              position 0;
            }
            bit remoteId {
              position 1;
            }
            bit vendorId {
              position 2;
            }
            bit clientId {
              position 3;
            }
            bit sourceMAC {
              position 4;
            }
            bit sourceIP {
              position 5;
            }
            bit userPattern {
              position 6;
            }
          }
          description
           "Login mask for the current pattern match. This is used to
            generate the UserId.";
          smiv2:defval "{circuitId}";
          smiv2:max-access read-write;
          smiv2:oid 1.3.6.1.4.1.1332.1.1.5.3.109.7.1.15;
        }

        leaf msanIsaTalPatternMatchRowStatus {
          type snmpv2-tc:RowStatus;
          description
           "The row status object controls the creation/deletion of rows
            in this table.
                                        Its semantics are the same as those for the RowStatus textual
            convention specified for SNMPv2.
            A new row is created using createAndWait(5)
            [createAndGo(4) is not supported]
            The value active(1) activates the entry.
                                        Setting this object to destroy6) will remove this entry.";
          smiv2:max-access read-write;
          smiv2:oid 1.3.6.1.4.1.1332.1.1.5.3.109.7.1.16;
        }
      }
    }

    container msanIsaTalPortPatternMatchTable {
      description
       "A connection between Pattern Matches and device ports.
        An entry is created in this table whenever a pattern match need to be
        attached to a downlink port.";
      smiv2:oid 1.3.6.1.4.1.1332.1.1.5.3.109.8;

      list msanIsaTalPortPatternMatchEntry {
        key "ifIndex msanIsaTalPatternMatchName";
        description
         "Each entry in this table contains the
          a unique pattern match on a port along with the loginmask to identify the user login packets.";
        smiv2:oid 1.3.6.1.4.1.1332.1.1.5.3.109.8.1;

        leaf ifIndex {
          type leafref {
            path "/if-mib:interfaces/if-mib:ifEntry/if-mib:ifIndex";
          }
        }

        leaf msanIsaTalPatternMatchName {
          type leafref {
            path "/iskratel-msan:ISKRATEL-MSAN-MIB/iskratel-msan:msanIsaTalPatternMatchTable/iskratel-msan:msanIsaTalPatternMatchEntry/iskratel-msan:msanIsaTalPatternMatchName";
          }
        }

        leaf msanIsaTalPortPatternMatchRowStatus {
          type snmpv2-tc:RowStatus;
          description
           "The row status object controls the creation/deletion of rows
            in this table.
            Its semantics are the same as those for the RowStatus textual
            convention specified for SNMPv2.
            Setting this object to createAndGo(4) creates a row in this table.
            Setting this object to destroy(6) will remove this entry.
            Read values: active(1).
            Other values are currently not supported.";
          smiv2:max-access read-write;
          smiv2:oid 1.3.6.1.4.1.1332.1.1.5.3.109.8.1.1;
        }
      }
    }

    container msanSyncTable {
      description
       "Description.";
      smiv2:oid 1.3.6.1.4.1.1332.1.1.5.3.110.2;

      list msanSyncEntry {
        key "msanSyncBoardPosition msanSyncSourcePriority";
        description
         "Description.";
        smiv2:oid 1.3.6.1.4.1.1332.1.1.5.3.110.2.1;

        leaf msanSyncBoardPosition {
          type int32 {
            range "1..20";
          }
          description
           "Central ethernet board position.";
          smiv2:max-access not-accessible;
          smiv2:oid 1.3.6.1.4.1.1332.1.1.5.3.110.2.1.1;
        }

        leaf msanSyncSourcePriority {
          type int32 {
            range "1..6";
          }
          description
           "Synchronization source priority: 1-first priority, 2-second priority.....";
          smiv2:max-access not-accessible;
          smiv2:oid 1.3.6.1.4.1.1332.1.1.5.3.110.2.1.2;
        }

        leaf msanSyncSourceType {
          type enumeration {
            enum ext-2mhz {
              value 4;
            }
            enum ext-10mhz {
              value 5;
            }
            enum ext-1hz {
              value 6;
            }
            enum mlvds-bp {
              value 8;
            }
            enum pps-bp {
              value 14;
            }
            enum ptp-eth {
              value 15;
            }
            enum sync-eth {
              value 16;
            }
            enum free-run {
              value 40;
            }
          }
          description
           "Synchronization source type:
            ext-2mhz(4) - synchronization on extended source 2MHz,
            ext-10mhz(5) - synchronization on extended source 10MHz,
            ext-1hz(6) - synchronization on extended source 1Hz,
            mlvds-bp(8) - synchronization on MLVDS,
            pps-bp(14) - synchronization on PPS,
            ptp-eth(15)- synchronization on PtP Ethernet,
            sync-eth(16) - synchronization on Synchronous Ethernet,
            free-run(40) - free-run synchronization";
          smiv2:max-access read-write;
          smiv2:oid 1.3.6.1.4.1.1332.1.1.5.3.110.2.1.3;
        }

        leaf msanSyncSourceId {
          type enumeration {
            enum input-1 {
              value 1;
            }
            enum input-2 {
              value 2;
            }
          }
          description
           "Synchronization source identity.
            
            msanSyncSourceId can be used when msanSyncSourceType has one of values:
            - ext-2mhz(4),
            - ext-10mhz(5),
            - ext-1hz(6),
            - mlvds-bp(8),
            - pps-bp(14),
            - free-run(40)
            
            msanSyncSourceId can be set only to input-1(1), when msanSyncSourceType
            is pps-bp(14) or free-run(40).";
          smiv2:max-access read-write;
          smiv2:oid 1.3.6.1.4.1.1332.1.1.5.3.110.2.1.4;
        }

        leaf msanSyncSourceEthPortId {
          type if-mib:InterfaceIndex;
          description
           "Synchronization source ethernet Port Id (value of ifIndex).
            
            msanSyncSourceEthPortId can be used, when msanSyncSourceType
            has ptp-eth(15) or sync-eth(16) value.";
          smiv2:max-access read-write;
          smiv2:oid 1.3.6.1.4.1.1332.1.1.5.3.110.2.1.5;
        }

        leaf msanSyncDestinationType {
          type enumeration {
            enum local {
              value 0;
            }
            enum global {
              value 10;
            }
          }
          description
           "Synchronization destination type:
            local(0) - synchronization signal is used only on local board
            global(0) - synchronization signal is sent to MLVDS bus";
          smiv2:max-access read-write;
          smiv2:oid 1.3.6.1.4.1.1332.1.1.5.3.110.2.1.6;
        }

        leaf msanSyncDestinationMlvdsId {
          type enumeration {
            enum mlvds-1 {
              value 1;
            }
            enum mlvds-2 {
              value 2;
            }
          }
          description
           "Destination MLVDS bus Identity.
            This parameter is used when msanSyncDestinationType has global(1) value.";
          smiv2:max-access read-write;
          smiv2:oid 1.3.6.1.4.1.1332.1.1.5.3.110.2.1.7;
        }

        leaf msanSyncSourceSuitability {
          type enumeration {
            enum undefined {
              value 0;
            }
            enum suitable {
              value 1;
            }
            enum unsuitable {
              value 2;
            }
          }
          description
           "Source Suitability.";
          smiv2:max-access read-only;
          smiv2:oid 1.3.6.1.4.1.1332.1.1.5.3.110.2.1.8;
        }

        leaf msanSyncSourceActivity {
          type enumeration {
            enum undefined {
              value 0;
            }
            enum active {
              value 1;
            }
            enum inactive {
              value 2;
            }
          }
          description
           "Source Activity .";
          smiv2:max-access read-only;
          smiv2:oid 1.3.6.1.4.1.1332.1.1.5.3.110.2.1.9;
        }

        leaf msanSyncRowStatus {
          type snmpv2-tc:RowStatus;
          description
           "The row status object controls the creation/deletion of rows in this table.
            Its semantics are the same as those for the RowStatus textual convention specified for SNMPv2.
            For row creation use createAndWait(5).
            For row activation use active(1).
            For row deletion use destroy(6).
            
            Other values are currently not supported.
            
            For row activation next terms must be defined
            - msanSyncSourceType
            - msanSyncSourceMlvdsId or msanSyncSourcePortId
            - msanSyncDestionationType
            - msanSyncDestionaMlvdsId if msanSyncDestionType=global(10)";
          smiv2:max-access read-write;
          smiv2:oid 1.3.6.1.4.1.1332.1.1.5.3.110.2.1.10;
        }
      }
    }

    container msanOnuCfgTable {
      description
       " ";
      smiv2:oid 1.3.6.1.4.1.1332.1.1.5.3.111.2;

      list msanOnuCfgEntry {
        key msanOnuCfgIfName;
        description
         "Row Description";
        smiv2:oid 1.3.6.1.4.1.1332.1.1.5.3.111.2.1;

        leaf msanOnuCfgIfName {
          type if:interface-ref;
          description
           "ONU interface name.";
          smiv2:max-access not-accessible;
        }

        leaf msanOnuCfgPassword {
          type rfc1213-mib:DisplayString {
            length "0..20";
          }
          description
           "The expected password of the ONU.";
          smiv2:max-access read-write;
          smiv2:oid 1.3.6.1.4.1.1332.1.1.5.3.111.2.1.2;
        }

        leaf msanOnuCfgEnablePm {
          type enumeration {
            enum enable {
              value 1;
            }
            enum disable {
              value 2;
            }
          }
          description
           "ONU  PM (Performance Management) collection. ";
          smiv2:max-access read-write;
          smiv2:oid 1.3.6.1.4.1.1332.1.1.5.3.111.2.1.3;
        }

        leaf msanOnuCfgSerialNumber {
          type rfc1213-mib:DisplayString {
            length "16";
          }
          description
           "The expected serial number, which  is unique for each ONU. It is defined in ITU-T G.984.3
            and contains the vendor id and version number. The first four bytes are an ASCII encoded
            vendor ID four letter mnemonic. The second four bytes are a binary encoded serial number,
            under the control of the ONT vendor. (R) (mandatory) (8 bytes).";
          smiv2:max-access read-write;
          smiv2:oid 1.3.6.1.4.1.1332.1.1.5.3.111.2.1.4;
        }

        leaf msanOnuCfgAdminState {
          type enumeration {
            enum enable {
              value 1;
            }
            enum disable {
              value 2;
            }
          }
          description
           "This attribute enable(1) and disable(2) the functions performed by this managed entity.
            When the administrative state is set to disable(lock), all user functions are blocked, and alarms, TCAs
            and AVCs for this managed entity and all dependent managed entities are no longer generated. ";
          smiv2:max-access read-write;
          smiv2:oid 1.3.6.1.4.1.1332.1.1.5.3.111.2.1.5;
        }

        leaf msanOnuCfgOnuDhcpMode {
          type enumeration {
            enum enable {
              value 1;
            }
            enum disable {
              value 2;
            }
          }
          description
           "ONU DHCP client mode.";
          smiv2:max-access read-write;
          smiv2:oid 1.3.6.1.4.1.1332.1.1.5.3.111.2.1.6;
        }

        leaf msanOnuCfgOnuIpAddress {
          type inet:ipv4-address;
          description
           "The current IP address of the ONU. This column can be written only if the DHCP mode
            is set to false. If the DHCP mode is set to true, this column can NOT be written.";
          smiv2:max-access read-write;
          smiv2:oid 1.3.6.1.4.1.1332.1.1.5.3.111.2.1.7;
        }

        leaf msanOnuCfgOnuIPMask {
          type inet:ipv4-address;
          description
           "The current IP Mask of the ONU. This column can be written only if the DHCP mode is
            set to false. If the DHCP mode is set to true, this column can NOT be written.";
          smiv2:max-access read-write;
          smiv2:oid 1.3.6.1.4.1.1332.1.1.5.3.111.2.1.8;
        }

        leaf msanOnuCfgOnuDefaultGateway {
          type inet:ipv4-address;
          description
           "The current default gateway of the ONU. This column can be written only if the DHCP
            mode is set to false. If the DHCP mode is set to true, this column can NOT be written.";
          smiv2:max-access read-write;
          smiv2:oid 1.3.6.1.4.1.1332.1.1.5.3.111.2.1.9;
        }

        leaf msanOnuCfgOnuReset {
          type enumeration {
            enum enable {
              value 1;
            }
            enum disable {
              value 2;
            }
          }
          description
           "Set this option to �enable�to initiate a reboot action on the ONU. This column can be
            used to reboot the ONU after Software upgrade. After the reboot command is sent to the ONU,
            this column is set to �disable�again by the OLT application. ";
          smiv2:max-access read-write;
          smiv2:oid 1.3.6.1.4.1.1332.1.1.5.3.111.2.1.10;
        }

        leaf msanOnuCfgOnuResetBackupImage {
          type enumeration {
            enum enable {
              value 1;
            }
            enum disable {
              value 2;
            }
          }
          description
           "Set this option to 'enable' to initiate a reboot action on the ONU and
            switch to a backup SW image.";
          smiv2:max-access read-write;
          smiv2:oid 1.3.6.1.4.1.1332.1.1.5.3.111.2.1.11;
        }

        leaf msanOnuCfgDefaultConfigFile {
          type rfc1213-mib:DisplayString;
          description
           "ONU config default file (this is reference to msanOnuDefaultConfigFileName).";
          smiv2:max-access read-write;
          smiv2:oid 1.3.6.1.4.1.1332.1.1.5.3.111.2.1.12;
        }

        leaf msanOnuCfgSendConfig {
          type enumeration {
            enum enable {
              value 1;
            }
            enum disable {
              value 2;
            }
          }
          description
           "Send default config file and config attributes to ONU.";
          smiv2:defval disable;
          smiv2:max-access read-write;
          smiv2:oid 1.3.6.1.4.1.1332.1.1.5.3.111.2.1.13;
        }

        leaf msanOnuCfgSendConfigStatus {
          type enumeration {
            enum ok {
              value 1;
            }
            enum pending {
              value 2;
            }
            enum notApplicable {
              value 3;
            }
            enum error {
              value 4;
            }
            enum wrongStatus {
              value 5;
            }
            enum notStarted {
              value 6;
            }
          }
                    config false;

          description
           "Status of sending default config file and config attributes to ONU.";
          smiv2:defval notStarted;
          smiv2:max-access read-only;
          smiv2:oid 1.3.6.1.4.1.1332.1.1.5.3.111.2.1.14;
        }
        leaf msanOnuCfgOnuResync {
          type enumeration {
            enum enable {
              value 1;
            }
            enum disable {
              value 2;
            }
          }
          description
           "Re-sync OMCI MIB";
          smiv2:defval disable;
          smiv2:max-access read-write;
          smiv2:oid 1.3.6.1.4.1.1332.1.1.5.3.111.2.1.15;
        }

        leaf msanOnuCfgOnuResetFactoryDefault {
          type enumeration {
            enum enable {
              value 1;
            }
            enum disable {
              value 2;
            }
          }
          description
           "Set this option to 'enable' to initiate a reboot to factory default action on the ONU.";
          smiv2:max-access read-write;
          smiv2:oid 1.3.6.1.4.1.1332.1.1.5.3.111.2.1.16;
        }
      }
    }

    container msanOnuInfoTable {
            config false;

      description
       " ";
      smiv2:oid 1.3.6.1.4.1.1332.1.1.5.3.111.3;

      list msanOnuInfoEntry {
        key msanOnuInfoIfName;
        description
         "Row Description";
        smiv2:oid 1.3.6.1.4.1.1332.1.1.5.3.111.3.1;

        leaf msanOnuInfoIfName {
          type if:interface-state-ref;
          description
           "ONU interface name.";
          smiv2:max-access not-accessible;
        }

        leaf msanOnuInfoPrimaryStatus {
          type enumeration {
            enum invalid {
              value 0;
            }
            enum inactive {
              value 1;
            }
            enum activatePending {
              value 2;
            }
            enum active {
              value 3;
            }
            enum deactivatePending {
              value 4;
            }
            enum disablePending {
              value 5;
            }
            enum disabled {
              value 6;
            }
          }
          description
           "invalid(0), inactive(1), activatePending(2), active(3),deactivatePending(4),
            disablePending(5), disabled(6) ";
          smiv2:max-access read-only;
          smiv2:oid 1.3.6.1.4.1.1332.1.1.5.3.111.3.1.2;
        }

        leaf msanOnuInfoEqualizationDelay {
          type uint32;
          description
           "Equalization delay for display.";
          smiv2:max-access read-only;
          smiv2:oid 1.3.6.1.4.1.1332.1.1.5.3.111.3.1.3;
        }

        leaf msanOnuInfoPowerLevel {
          type int32;
          description
           "Power level.";
          smiv2:max-access read-only;
          smiv2:oid 1.3.6.1.4.1.1332.1.1.5.3.111.3.1.4;
        }

        leaf msanOnuInfoVendorId {
          type rfc1213-mib:DisplayString {
            length "4";
          }
          description
           "This attribute identifies the vendor of the ONT.It is the same as
            the four most significant bytes of the ONT serial number as specified in
            ITU-T Rec. G.984.3. (R) (mandatory) (4 bytes). ";
          smiv2:max-access read-only;
          smiv2:oid 1.3.6.1.4.1.1332.1.1.5.3.111.3.1.5;
        }

        leaf msanOnuInfoVersion {
          type rfc1213-mib:DisplayString;
          description
           "This attribute identifies the version of the ONT as defined by the
            vendor. Then character value ��0�� indicates that version information is not
            available or applicable.";
          smiv2:max-access read-only;
          smiv2:oid 1.3.6.1.4.1.1332.1.1.5.3.111.3.1.7;
        }

        leaf msanOnuInfoTrafficManagementOption {
          type enumeration {
            enum priorityControlledAndFlexiblyScheduledUpstreamTraffic {
              value 0;
            }
            enum rateControlledUpstreamTraffic {
              value 1;
            }
          }
          description
           "This attribute identifies the upstream traffic management function implemented
            in the ONT. There are two options:
            0 Priority controlled and flexibly scheduled upstream traffic. The traffic scheduler and
            		priority queue mechanism are used for upstream traffic.
            1 Rate controlled upstream traffic. The maximum upstream traffic of each individual
            		connection is guaranteed";
          smiv2:defval priorityControlledAndFlexiblyScheduledUpstreamTraffic;
          smiv2:max-access read-only;
          smiv2:oid 1.3.6.1.4.1.1332.1.1.5.3.111.3.1.8;
        }

        leaf msanOnuInfoOperState {
          type enumeration {
            enum enabled {
              value 1;
            }
            enum disabled {
              value 2;
            }
            enum unknown {
              value 3;
            }
          }
          description
           "This attribute reports whether the managed entity is currently capable of performing its
            function.";
          smiv2:max-access read-only;
          smiv2:oid 1.3.6.1.4.1.1332.1.1.5.3.111.3.1.9;
        }

        leaf msanOnuInfoEquipmentId {
          type binary {
            length "20";
          }
          description
           "This attribute may be used to identify the specific type of ONT. In North America,
            this may be the equipment CLEI code. (R) (optional) (20 bytes).";
          smiv2:max-access read-only;
          smiv2:oid 1.3.6.1.4.1.1332.1.1.5.3.111.3.1.10;
        }

        leaf msanOnuInfoOmccVersion {
          type enumeration {
            enum g-984-4 {
              value 128;
            }
            enum g-984-4amd1 {
              value 129;
            }
            enum g-984-4amd2 {
              value 130;
            }
            enum g-984-4amd3 {
              value 131;
            }
            enum g-984-42007to2008 {
              value 132;
            }
          }
          description
           "This attribute identifies the version of the OMCC protocol being used by the ONT.
            This allows the OLT to manage a network with ONTs that support different OMCC versions.
            Release levels of G.984.4 may be supported with the following code points:
            0x80 G.984.4 06/04. Note: for historic reasons, this codepoint may also appear in ONTs that
            		support later versions of G.984.4.
            0x81 G.984.4 amd 1 (06/05) ITU-T Rec. G.984.4 (02/2008) 51
            0x82 G.984.4 amd 2 (03/06)
            0x83 G.984.4 amd 3 (12/06)
            0x84 G.984.4 2007-2008 current draft (R) (mandatory) (1 byte)";
          smiv2:max-access read-only;
          smiv2:oid 1.3.6.1.4.1.1332.1.1.5.3.111.3.1.11;
        }

        leaf msanOnuInfoOnuHardwareType {
          type uint32;
          description
           "Most significant byte of vendor product code which provides a vendor-specific product
            code for the ONT.(R) (optional) (2 bytes).";
          smiv2:max-access read-only;
          smiv2:oid 1.3.6.1.4.1.1332.1.1.5.3.111.3.1.12;
        }

        leaf msanOnuInfoHardwareRevision {
          type uint32;
          status obsolete;
          description
           "Least significant byte of vendor product code which provides a vendor-specific product
            code or the ONT.(R) (optional) (2 bytes). ";
          smiv2:max-access read-only;
          smiv2:oid 1.3.6.1.4.1.1332.1.1.5.3.111.3.1.13;
        }

        leaf msanOnuInfoSecurityCapability {
          type uint32 {
            range "1..255";
          }
          description
           "This attribute advertises the security capabilities of the ONT. The following codepoints
            are defined:
            1 Reserved
            2 AES
            3..255 Reserved (R) (mandatory) (1 byte). ";
          smiv2:defval 2;
          smiv2:max-access read-only;
          smiv2:oid 1.3.6.1.4.1.1332.1.1.5.3.111.3.1.14;
        }

        leaf msanOnuInfoTotalPriorityQueueNumber {
          type uint32;
          description
           "This attribute reports the total number of priority queues that are not associated with
            a circuit pack, but with the ONT in its entirety. The maximum value is 0x0FFF. Upon ME instantiation,
            he ONT sets this attribute to the value that represents its capabilities. (R) (mandatory) (2 bytes). ";
          smiv2:max-access read-only;
          smiv2:oid 1.3.6.1.4.1.1332.1.1.5.3.111.3.1.15;
        }

        leaf msanOnuInfoTotalTrafficSchedulerNumber {
          type uint32;
          description
           "This attribute reports the total number of traffic schedulers that are not associated
            with a circuit pack, but with the ONT in its entirety. The ONT supports null function, HOL scheduling
            and WRR from the priority control and guarantee of minimum rate control points of view, respectively.
            If the ONT has no traffic schedulers, this attribute is 0. (R) (mandatory) (1 byte).";
          smiv2:max-access read-only;
          smiv2:oid 1.3.6.1.4.1.1332.1.1.5.3.111.3.1.16;
        }

        leaf msanOnuInfoTotalGemPortNumber {
          type uint32 {
            range "0..4095";
          }
          description
           "This attribute reports the total number of GEM port-IDs supported by the ONT. The maximum
            value is 0x0FFF. Upon ME instantiation, the ONT sets this attribute to the value that represents
            its capabilities. (R) (optional) (2 bytes).";
          smiv2:max-access read-only;
          smiv2:oid 1.3.6.1.4.1.1332.1.1.5.3.111.3.1.17;
        }

        leaf msanOnuInfoTotalTcontNumber {
          type uint32;
          description
           "This attribute reports the total number of T-CONTs supported by the ONT.";
          smiv2:max-access read-only;
          smiv2:oid 1.3.6.1.4.1.1332.1.1.5.3.111.3.1.18;
        }

        leaf msanOnuInfoTotalEthernetUniNumber {
          type uint32;
          description
           "The number of Ethernet UNI ports.";
          smiv2:max-access read-only;
          smiv2:oid 1.3.6.1.4.1.1332.1.1.5.3.111.3.1.19;
        }

        leaf msanOnuInfoTotalPotsUniNumber {
          type uint32;
          description
           "The number of POTS UNI ports.";
          smiv2:max-access read-only;
          smiv2:oid 1.3.6.1.4.1.1332.1.1.5.3.111.3.1.20;
        }

        leaf msanOnuInfoSysUpTime {
          type uint32;
          description
           "This attribute counts the 10 ms intervals since the ONT was last initialized. It rolls
            over to 0 when full. (See RFC 1213.) (R) (optional) (4 bytes).";
          smiv2:max-access read-only;
          smiv2:oid 1.3.6.1.4.1.1332.1.1.5.3.111.3.1.21;
        }

        leaf msanOnuInfoOnuImageInstance0Version {
          type rfc1213-mib:DisplayString;
          description
           "This attribute identifies the version of the ONT as defined by the
            vendor. Then character value ��0�� indicates that version information is not
            available or applicable. (R) (mandatory) (14 bytes).";
          smiv2:max-access read-only;
          smiv2:oid 1.3.6.1.4.1.1332.1.1.5.3.111.3.1.22;
        }

        leaf msanOnuInfoOnuImageInstance0Valid {
          type boolean;
          description
           "The valid flag of ONU image instance 0.";
          smiv2:max-access read-only;
          smiv2:oid 1.3.6.1.4.1.1332.1.1.5.3.111.3.1.23;
        }

        leaf msanOnuInfoOnuImageInstance0Activate {
          type boolean;
          description
           "The activate flag of ONU image instance 0.";
          smiv2:max-access read-only;
          smiv2:oid 1.3.6.1.4.1.1332.1.1.5.3.111.3.1.24;
        }

        leaf msanOnuInfoOnuImageInstance0Commit {
          type boolean;
          description
           "The commit flag of ONU image instance 0.";
          smiv2:max-access read-only;
          smiv2:oid 1.3.6.1.4.1.1332.1.1.5.3.111.3.1.25;
        }

        leaf msanOnuInfoOnuImageInstance1Version {
          type rfc1213-mib:DisplayString;
          description
           "This attribute identifies the version of the ONT as defined by the
            vendor. Then character value ��0�� indicates that version information is not
            available or applicable. (R) (mandatory) (14 bytes). ";
          smiv2:max-access read-only;
          smiv2:oid 1.3.6.1.4.1.1332.1.1.5.3.111.3.1.26;
        }

        leaf msanOnuInfoOnuImageInstance1Valid {
          type boolean;
          description
           "The valid flag of ONU image instance 1 ";
          smiv2:max-access read-only;
          smiv2:oid 1.3.6.1.4.1.1332.1.1.5.3.111.3.1.27;
        }

        leaf msanOnuInfoOnuImageInstance1Activate {
          type boolean;
          description
           "The activate flag of ONU image instance 1.";
          smiv2:max-access read-only;
          smiv2:oid 1.3.6.1.4.1.1332.1.1.5.3.111.3.1.28;
        }

        leaf msanOnuInfoOnuImageInstance1Commit {
          type boolean;
          description
           "The commit flag of ONU image instance 1.";
          smiv2:max-access read-only;
          smiv2:oid 1.3.6.1.4.1.1332.1.1.5.3.111.3.1.29;
        }

        leaf msanOnuInfoOnuMacAddress {
          type yang:mac-address;
          description
           "The MAC address of the ONU in hexadecimal format.";
          smiv2:max-access read-only;
          smiv2:oid 1.3.6.1.4.1.1332.1.1.5.3.111.3.1.30;
        }

        leaf msanOnuInfoOnuDhcpMode {
          type boolean;
          description
           "ONU DHCP mode:
            1 Enabled
            2 Disabled ";
          smiv2:defval false;
          smiv2:max-access read-only;
          smiv2:oid 1.3.6.1.4.1.1332.1.1.5.3.111.3.1.31;
        }

        leaf msanOnuInfoOnuIpAddress {
          type inet:ipv4-address;
          description
           "The current IP address of the ONU. ";
          smiv2:max-access read-only;
          smiv2:oid 1.3.6.1.4.1.1332.1.1.5.3.111.3.1.32;
        }

        leaf msanOnuInfoOnuIpMask {
          type inet:ipv4-address;
          description
           "The current IP Mask of the ONU. ";
          smiv2:max-access read-only;
          smiv2:oid 1.3.6.1.4.1.1332.1.1.5.3.111.3.1.33;
        }

        leaf msanOnuInfoOnuDefaultGateway {
          type inet:ipv4-address;
          description
           "The current default gateway of the ONU. ";
          smiv2:max-access read-only;
          smiv2:oid 1.3.6.1.4.1.1332.1.1.5.3.111.3.1.34;
        }

        leaf msanOnuInfoOnuFastLeaveCapability {
          type uint32 {
            range "0..16";
          }
          description
           "This attribute specifies Fast leave capability. It��s carried in a proprietary OMCI remote DEBUG ME,
            Bit value 0 not support
            Bit value 1 support
            
            Bit 0 fast leave in CTC distributed mode
            Bit 1 non fast leave in CTC distributed mode
            Bit 2 fast leave in CTC controllable mode
            Bit 3 non fast leave in CTC controllable mode";
          smiv2:defval 2;
          smiv2:max-access read-only;
          smiv2:oid 1.3.6.1.4.1.1332.1.1.5.3.111.3.1.35;
        }

        leaf msanOnuInfoSerialNumber {
          type rfc1213-mib:DisplayString {
            length "16";
          }
          description
           "Current serial number, which  is unique for each ONU. It is defined in ITU-T G.984.3
            and contains the vendor id and version number. The first four bytes are an ASCII encoded
            vendor ID four letter mnemonic. The second four bytes are a binary encoded serial number,
            under the control of the ONT vendor. (R) (mandatory) (8 bytes).";
          smiv2:max-access read-only;
          smiv2:oid 1.3.6.1.4.1.1332.1.1.5.3.111.3.1.36;
        }

        leaf msanOnuInfoPassword {
          type rfc1213-mib:DisplayString {
            length "0..20";
          }
          description
           "Received password of the ONU.";
          smiv2:max-access read-only;
          smiv2:oid 1.3.6.1.4.1.1332.1.1.5.3.111.3.1.37;
        }

        leaf msanOnuInfoRxPower {
          type int32;
          units "0.01 dBm";
          description
           "ONU receive (Rx) power measurement.";
          smiv2:max-access read-only;
          smiv2:oid 1.3.6.1.4.1.1332.1.1.5.3.111.3.1.38;
        }

        leaf msanOnuInfoTxPower {
          type int32;
          units "0.01 dBm";
          description
           "ONU transmit (Tx) power measurement.";
          smiv2:max-access read-only;
          smiv2:oid 1.3.6.1.4.1.1332.1.1.5.3.111.3.1.39;
        }

        leaf msanOnuInfoOltRxPower {
          type int32;
          units "0.01 dBm";
          description
           "OLT receive (Rx) power measurement.";
          smiv2:max-access read-only;
          smiv2:oid 1.3.6.1.4.1.1332.1.1.5.3.111.3.1.40;
        }

        leaf msanOnuInfoTemp {
          type int32;
          units Celsius;
          description
           "ONU current temperature (in Celsius).";
          smiv2:max-access read-only;
          smiv2:oid 1.3.6.1.4.1.1332.1.1.5.3.111.3.1.41;
        }
      }
    }

    container msanOnuUpgradeTable {
      description
       "Description.";
      smiv2:oid 1.3.6.1.4.1.1332.1.1.5.3.111.4;

      list msanOnuUpgradeEntry {
        key msanOnuUpgradeMethod;
        description
         "Description.";
        smiv2:oid 1.3.6.1.4.1.1332.1.1.5.3.111.4.1;

        leaf msanOnuUpgradeMethod {
          type enumeration {
            enum manual {
              value 1;
            }
            enum scheduled {
              value 2;
            }
            enum automatic {
              value 3;
            }
          }
          description
           " 	1 Manual - in which the EMS initiates upgrade operation.
            Manual upgrade procedure starts when global parameter msanOnuUpgradeMethodManualStart
                    is set to enable.
            
            2 Scheduled - in which the EMS specifies the ONU list and the time when the upgrade
            should start. Only one scheduled task entry can exist in the table, and it is  always valid even
                   after their execution.
            
            3 Automatic - in which the ONU is upgraded automatically when it is
            discovered. Only one automatic task entry can exist in the
            table, and it is always valid even after its execution. ";
          smiv2:max-access not-accessible;
          smiv2:oid 1.3.6.1.4.1.1332.1.1.5.3.111.4.1.1;
        }

        leaf msanOnuUpgradeOption {
          type enumeration {
            enum normal {
              value 1;
            }
            enum forced {
              value 2;
            }
          }
                    config false;

          description
           "ONU upgrade option:
            1 Normal. If the target version is newer than the current version, then the image download will start.
            2 Forced. The image download will always start. ";
          smiv2:defval normal;
          smiv2:max-access read-write;
          smiv2:oid 1.3.6.1.4.1.1332.1.1.5.3.111.4.1.2;
        }

        leaf msanOnuUpgradeRebootMode {
          type enumeration {
            enum automatic {
              value 1;
            }
            enum manual {
              value 2;
            }
            enum scheduled {
              value 3;
            }
          }
          description
           "It defines the reboot action after the image is downloaded to the ONU:
            1 - Automatic. ONU will be rebooted during image activation. The complete upgrade
                procedure will be executed automatically: download -> activate (reboot) -> commit.
            2 - Manual. The following upgrade procedure will be executed: download -> commit. The
                ONU can be rebooted via onuReset of ONU configuration table.
            3 - Scheduled. The ONU will be rebooted automatically at onuUpgradeRebootScheduledTime. The
                following upgrade procedure will be executed: download -> commit -> activate (reboot) at
                onuUpgradeRebootScheduledTime. ";
          smiv2:defval automatic;
          smiv2:max-access read-write;
          smiv2:oid 1.3.6.1.4.1.1332.1.1.5.3.111.4.1.3;
        }

        leaf msanOnuUpgradeImageInstance {
          type int32;
          status obsolete;
          description
           "ONU image instance selection:
            1 Automatic. The instance which is not committed will be upgraded. For ONU which
             has only one image instance, OLT will always upgrade this image instance 0";
          smiv2:defval 1;
          smiv2:max-access read-write;
          smiv2:oid 1.3.6.1.4.1.1332.1.1.5.3.111.4.1.4;
        }

        leaf msanOnuUpgradeScheduledTime {
          type rfc1213-mib:DisplayString;
          units hh:mm:ss;
          description
           "The time at which the ONU will be upgraded scheduledly. This column is used only if the
            msanOnuUpgradeMethod is set to 2 - Scheduled. The format of the string is hh:mm:ss which means
            the upgrade can be repeated every 24 hours.";
          smiv2:defval 23:30:00;
          smiv2:max-access read-write;
          smiv2:oid 1.3.6.1.4.1.1332.1.1.5.3.111.4.1.5;
        }

        leaf msanOnuUpgradeRebootScheduledTime {
          type rfc1213-mib:DisplayString;
          units " hh:mm:ss";
          description
           "The time at which the ONU will be rebooted. This column is used only if the msanOnuUpgradeRebootMode
            is set to 3, Scheduled. The format of the string is hh:mm:ss which means the reboot can be repeated
            every 24 hours after a successful upgrade. The reboot on a particular ONU should not happen if there is
            no any actual upgrade on it. ";
          smiv2:max-access read-write;
          smiv2:oid 1.3.6.1.4.1.1332.1.1.5.3.111.4.1.6;
        }

        leaf msanOnuUpgradeParticipantPortListBitMap {
          type binary {
            length "0..2048";
          }
          description
           "ONU upgrade participant port list bit map.To include an ONU in upgrade, set the corresponding bit to 1.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-write;
          smiv2:oid 1.3.6.1.4.1.1332.1.1.5.3.111.4.1.7;
        }

        leaf msanOnuUpgradeProgressDownloadPortListBitMap {
          type binary {
            length "0..2048";
          }
                    config false;

          description
           "ONU upgrade progress download port list bit map. Since an ONU enters the image download stage, the corresponding
            bit representing this ONU will remain as 1.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-only;
          smiv2:oid 1.3.6.1.4.1.1332.1.1.5.3.111.4.1.8;
        }

        leaf msanOnuUpgradeProgressActivatePortListBitMap {
          type binary {
            length "0..2048";
          }
                    config false;

          description
           "ONU upgrade progress activate port list bit map. Since an ONU enters image activate stage, the corresponding bit
            representing this ONU will remain as 1.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-only;
          smiv2:oid 1.3.6.1.4.1.1332.1.1.5.3.111.4.1.9;
        }

        leaf msanOnuUpgradeProgressCommitPortListBitMap {
          type binary {
            length "0..2048";
          }
                    config false;

          description
           "ONU upgrade progress commit port list bit map. Since an ONU enters image commit stage, the corresponding bit representing
            this ONU will remain as 1.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-only;
          smiv2:oid 1.3.6.1.4.1.1332.1.1.5.3.111.4.1.10;
        }

        leaf msanOnuUpgradeProgressFinalPortListBitMap {
          type binary {
            length "0..2048";
          }
                    config false;

          description
           "ONU upgrade progress final port list bit map. Whenever the upgrade procedure for an ONU is finished, regardless of success
            or failure, the corresponding bit representing this ONU will become 1.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-only;
          smiv2:oid 1.3.6.1.4.1.1332.1.1.5.3.111.4.1.11;
        }

        leaf msanOnuUpgradeResultFinalPortListBitMap {
          type binary {
            length "0..2048";
          }
                    config false;

          description
           "ONU upgrade result port list bit map. Whenever an ONU encounters failure in any stage, then the corresponding bit representing
            this ONU will become 1, and the upgrade procedure won't proceed to the next stage for this particular ONU.
            It's assumed that each slot has 8 or 16 OLT PON ports and each OLT PON port has 128 ONUs.Nonexist ports in the
            port list bit map should be reserved and set to 0 if the actual capacity of PON ports and ONUs of the line
            card in the slot is less than the above maximum assumption";
          smiv2:defval "";
          smiv2:max-access read-only;
          smiv2:oid 1.3.6.1.4.1.1332.1.1.5.3.111.4.1.12;
        }
      }
    }

    container msanOnuUpgradeHwTypeTable {
      description
       "Description.";
      smiv2:oid 1.3.6.1.4.1.1332.1.1.5.3.111.5;

      list msanOnuUpgradeHwTypeEntry {
        key "msanOnuUpgradeHwTypeVendorId msanOnuUpgradeHwTypeHwType msanOnuUpgradeHwTypeMethod";
        description
         "Description.";
        smiv2:oid 1.3.6.1.4.1.1332.1.1.5.3.111.5.1;

        leaf msanOnuUpgradeHwTypeVendorId {
          type rfc1213-mib:DisplayString {
            length "4";
          }
          description
           "Description.";
          smiv2:max-access not-accessible;
          smiv2:oid 1.3.6.1.4.1.1332.1.1.5.3.111.5.1.1;
        }

        leaf msanOnuUpgradeHwTypeHwType {
          type int32;
          description
           "ONU model which need firmware upgrade.";
          smiv2:max-access not-accessible;
          smiv2:oid 1.3.6.1.4.1.1332.1.1.5.3.111.5.1.2;
        }

        leaf msanOnuUpgradeHwTypeMethod {
          type enumeration {
            enum manual {
              value 1;
            }
            enum scheduled {
              value 2;
            }
            enum automatic {
              value 3;
            }
          }
          description
           "Upgrade method:
            1 Manual
            2 Scheduled
            3 Automatic.";
          smiv2:max-access not-accessible;
          smiv2:oid 1.3.6.1.4.1.1332.1.1.5.3.111.5.1.3;
        }

        leaf msanOnuUpgradeHwTypeHwRevision {
          type rfc1213-mib:DisplayString {
            length "0..63";
          }
          status obsolete;
          description
           "ONU upgrade hardware revision.";
          smiv2:defval "";
          smiv2:max-access read-write;
          smiv2:oid 1.3.6.1.4.1.1332.1.1.5.3.111.5.1.4;
        }

        leaf msanOnuUpgradeHwTypeFwRevision {
          type rfc1213-mib:DisplayString {
            length "0..28";
          }
          description
           "ONU upgrade firmware revision. ";
          smiv2:defval 0.0;
          smiv2:max-access read-write;
          smiv2:oid 1.3.6.1.4.1.1332.1.1.5.3.111.5.1.5;
        }

        leaf msanOnuUpgradeHwTypeImageName {
          type rfc1213-mib:DisplayString {
            length "0..256";
          }
          description
           "ONU upgrade image name.";
          smiv2:max-access read-write;
          smiv2:oid 1.3.6.1.4.1.1332.1.1.5.3.111.5.1.6;
        }

        leaf msanOnuUpgradeHwTypeImagePath {
          type rfc1213-mib:DisplayString {
            length "0..112";
          }
          description
           "ONU upgrade image folder path.";
          smiv2:defval "";
          smiv2:max-access read-write;
          smiv2:oid 1.3.6.1.4.1.1332.1.1.5.3.111.5.1.7;
        }

        leaf msanOnuUpgradeHwTypeServerName {
          type rfc1213-mib:DisplayString {
            length "0..16";
          }
          description
           "ONU upgrade server name.
            This is a parameter msanOnuUpgradeServerName from msanOnuUpgradeServerTable.";
          smiv2:max-access read-write;
          smiv2:oid 1.3.6.1.4.1.1332.1.1.5.3.111.5.1.8;
        }
      }
    }

    container msanOnuVirtGemPortInfoTable {
      description
       "Description.";
      smiv2:oid 1.3.6.1.4.1.1332.1.1.5.3.111.6;

      list msanOnuVirtGemPortInfoEntry {
        key msanOnuVirtGemPortInfoIfName;
        description
         "Description.";
        smiv2:oid 1.3.6.1.4.1.1332.1.1.5.3.111.6.1;

        leaf msanOnuVirtGemPortInfoIfName {
          type if:interface-state-ref;
          description
           "Index of Virtual GEM Port (from ifTable).";
          smiv2:max-access not-accessible;
          smiv2:oid 1.3.6.1.4.1.1332.1.1.5.3.111.6.1.1;
        }

        leaf msanOnuVirtGemPortInfoOltGemPortNo {
          type yang:gauge32;
          description
           "GEM port no which is assigned dynamically by OLT.";
          smiv2:max-access read-only;
          smiv2:oid 1.3.6.1.4.1.1332.1.1.5.3.111.6.1.2;
        }

        leaf msanOnuVirtGemPortInfoOltAllocId {
          type yang:gauge32;
          description
           "Alloc-ID which is assigned dynamically by OLT, a dynamic Alloc-ID is one-to-one mapped to
            a static T-CONT index.";
          smiv2:max-access read-only;
          smiv2:oid 1.3.6.1.4.1.1332.1.1.5.3.111.6.1.3;
        }

        leaf msanOnuVirtGemPortInfoTcontIndex {
          type yang:gauge32;
          description
           "Static T-CONT index from ONU's perspective.";
          smiv2:max-access read-only;
          smiv2:oid 1.3.6.1.4.1.1332.1.1.5.3.111.6.1.4;
        }
      }
    }

    container msanOnuVirtGemPortStatTable {
            config false;

      description
       "This table displays performance statistics for Virtual Gem Ports.";
      smiv2:oid 1.3.6.1.4.1.1332.1.1.5.3.111.7;

      list msanOnuVirtGemPortStatEntry {
        key "msanOnuVirtGemPortStatIfName msanOnuVirtGemPortStatIntervalId";
        description
         "Serves as an index for this table. Identifies the
          15 interval in which PM was collected. The value
          0 identifies the current interval. Value 1 identifies
          the latest 15 minute interval and value 96
          identifies the last 15 minute interval in a a 24 hour period.";
        smiv2:oid 1.3.6.1.4.1.1332.1.1.5.3.111.7.1;

        leaf msanOnuVirtGemPortStatIfName {
          type if:interface-state-ref;
          description
           "Index of Virtual GEM Port (from ifTable).";
          smiv2:max-access not-accessible;
          smiv2:oid 1.3.6.1.4.1.1332.1.1.5.3.111.7.1.1;
        }

        leaf msanOnuVirtGemPortStatIntervalId {
          type int32 {
            range "0..96";
          }
          description
           "Serves as an index for this table. Identifies the
            15 interval in which PM was collected. The value
            0 identifies the current interval. Value 1 identifies
            the latest 15 minute interval and value 96
            identifies the last 15 minute interval in a a 24 hour period.";
          smiv2:max-access not-accessible;
          smiv2:oid 1.3.6.1.4.1.1332.1.1.5.3.111.7.1.2;
        }

        leaf msanOnuVirtGemPortStatInFrames {
          type yang:counter64;
          description
           "The total number of gpon frames received on the interface.";
          smiv2:max-access read-only;
          smiv2:oid 1.3.6.1.4.1.1332.1.1.5.3.111.7.1.3;
        }

        leaf msanOnuVirtGemPortStatInOctets {
          type yang:counter64;
          description
           "The total number of octets received on the interface.";
          smiv2:max-access read-only;
          smiv2:oid 1.3.6.1.4.1.1332.1.1.5.3.111.7.1.4;
        }

        leaf msanOnuVirtGemPortStatOutFrames {
          type yang:counter64;
          description
           "The total number of gpon frames transmitted out of the
            interface.";
          smiv2:max-access read-only;
          smiv2:oid 1.3.6.1.4.1.1332.1.1.5.3.111.7.1.5;
        }

        leaf msanOnuVirtGemPortStatOutOctets {
          type yang:counter64;
          description
           "The total number of octets transmitted out of the
            interface";
          smiv2:max-access read-only;
          smiv2:oid 1.3.6.1.4.1.1332.1.1.5.3.111.7.1.6;
        }
      }
    }

    container msanOnuBlackListTable {
            config false;

      description
       "Table for displaying the ONUs in black list per OLT ports.";
      smiv2:oid 1.3.6.1.4.1.1332.1.1.5.3.111.8;

      list msanOnuBlackListEntry {
        key "msanOnuBlackListIfName msanOnuBlackListSerialNumber";
        description
         "Description.";
        smiv2:oid 1.3.6.1.4.1.1332.1.1.5.3.111.8.1;

        leaf msanOnuBlackListIfName {
          type if:interface-state-ref;
          description
           "Index of OLT port (from ifTable).";
          smiv2:max-access not-accessible;
          smiv2:oid 1.3.6.1.4.1.1332.1.1.5.3.111.8.1.1;
        }

        leaf msanOnuBlackListSerialNumber {
          type rfc1213-mib:DisplayString {
            length "16";
          }
          description
           "The serial number. Index for this table.
            The serial number is unique for each ONT.
            
            It is defined in ITU-T G.984.3 and contains
            the vendor id and version number. The first
            four bytes are an ASCII encoded vendor ID
            four letter mnemonic. The second four bytes
            are a binary encoded serial number, under the
            control of the ONT vendor. (R) (mandatory) (8 bytes).";
          smiv2:max-access not-accessible;
          smiv2:oid 1.3.6.1.4.1.1332.1.1.5.3.111.8.1.2;
        }

        leaf msanOnuBlackListPassword {
          type rfc1213-mib:DisplayString {
            length "0..20";
          }
          description
           "Received ONU password.";
          smiv2:max-access read-only;
          smiv2:oid 1.3.6.1.4.1.1332.1.1.5.3.111.8.1.3;
        }

        leaf msanOnuBlackListCause {
          type enumeration {
            enum invalid {
              value 1;
            }
            enum unknownSerialnum {
              value 2;
            }
            enum passwordMismatch {
              value 3;
            }
          }
          description
           "The cause of entering black list.";
          smiv2:max-access read-only;
          smiv2:oid 1.3.6.1.4.1.1332.1.1.5.3.111.8.1.4;
        }
      }
    }

    container msanOnuUpgradeServerTable {
      description
       "Description.";
      smiv2:oid 1.3.6.1.4.1.1332.1.1.5.3.111.9;

      list msanOnuUpgradeServerEntry {
        key msanOnuUpgradeServerName;
        description
         "Description.";
        smiv2:oid 1.3.6.1.4.1.1332.1.1.5.3.111.9.1;

        leaf msanOnuUpgradeServerName {
          type rfc1213-mib:DisplayString {
            length "0..16";
          }
          description
           "ONU SW upgrade server name.";
          smiv2:max-access not-accessible;
          smiv2:oid 1.3.6.1.4.1.1332.1.1.5.3.111.9.1.1;
        }

        leaf msanOnuUpgradeServerIpAddress {
          type inet:ipv4-address;
          description
           "ONU SW upgrade server IP address.";
          smiv2:max-access read-write;
          smiv2:oid 1.3.6.1.4.1.1332.1.1.5.3.111.9.1.2;
        }

        leaf msanOnuUpgradeServerUserName {
          type rfc1213-mib:DisplayString {
            length "0..16";
          }
          description
           "Username used in ONU SW upgrade protocol.";
          smiv2:defval anonymous;
          smiv2:max-access read-write;
          smiv2:oid 1.3.6.1.4.1.1332.1.1.5.3.111.9.1.3;
        }

        leaf msanOnuUpgradeServerUserPassword {
          type rfc1213-mib:DisplayString {
            length "0..32";
          }
          description
           "User password used in ONU SW upgrade protocol.";
          smiv2:defval anonymous;
          smiv2:max-access read-write;
          smiv2:oid 1.3.6.1.4.1.1332.1.1.5.3.111.9.1.4;
        }

        leaf msanOnuUpgradeServerProtocol {
          type enumeration {
            enum ftp {
              value 1;
            }
          }
          description
           "ONU SW upgrade protocol type.";
          smiv2:defval ftp;
          smiv2:max-access read-write;
          smiv2:oid 1.3.6.1.4.1.1332.1.1.5.3.111.9.1.5;
        }

        leaf msanOnuUpgradeServerProtocolPortId {
          type int32 {
            range "0..65535";
          }
          description
           "ONU SW upgrade protocol port number.
            
            If value is set to 0, standard protocol number is used.";
          smiv2:max-access read-write;
          smiv2:oid 1.3.6.1.4.1.1332.1.1.5.3.111.9.1.6;
        }
      }
    }

    container msanOnuEthPortInfoTable {
            config false;

      description
       "Description.";
      smiv2:oid 1.3.6.1.4.1.1332.1.1.5.3.111.10;

      list msanOnuEthPortInfoEntry {
        key "msanOnuEthPortInfoOnuIfName msanOnuEthPortInfoUniId";
        description
         "Description.";
        smiv2:oid 1.3.6.1.4.1.1332.1.1.5.3.111.10.1;

        leaf msanOnuEthPortInfoOnuIfName {
          type if:interface-state-ref;
          description
           "Index of ONU (from ifTable).";
          smiv2:max-access not-accessible;
          smiv2:oid 1.3.6.1.4.1.1332.1.1.5.3.111.10.1.1;
        }

        leaf msanOnuEthPortInfoUniId {
          type int32;
          description
           "ONU Ethernet Port (UNI) identifier.";
          smiv2:max-access not-accessible;
          smiv2:oid 1.3.6.1.4.1.1332.1.1.5.3.111.10.1.2;
        }

        leaf msanOnuEthPortInfoAdminState {
          type enumeration {
            enum enable {
              value 1;
            }
            enum disable {
              value 2;
            }
            enum notAvailable {
              value 3;
            }
          }
          description
           "ONU eth port (UNI) administration state.";
          smiv2:max-access read-only;
          smiv2:oid 1.3.6.1.4.1.1332.1.1.5.3.111.10.1.3;
        }

        leaf msanOnuEthPortInfoOperState {
          type enumeration {
            enum up {
              value 1;
            }
            enum down {
              value 2;
            }
            enum notAvailable {
              value 3;
            }
          }
          description
           "ONU eth port (UNI) operational state.";
          smiv2:max-access read-only;
          smiv2:oid 1.3.6.1.4.1.1332.1.1.5.3.111.10.1.4;
        }

        leaf msanOnuEthPortInfoSpeed {
          type enumeration {
            enum mbps10 {
              value 1;
            }
            enum mbps100 {
              value 2;
            }
            enum mbps1000 {
              value 3;
            }
            enum notAvailable {
              value 4;
            }
          }
          description
           "Speed of ONU eth port (UNI).";
          smiv2:max-access read-only;
          smiv2:oid 1.3.6.1.4.1.1332.1.1.5.3.111.10.1.6;
        }

        leaf msanOnuEthPortInfoDuplex {
          type enumeration {
            enum full {
              value 1;
            }
            enum half {
              value 2;
            }
            enum notAvailable {
              value 3;
            }
          }
          description
           "Duplex mode of ONU eth port (UNI).";
          smiv2:max-access read-only;
          smiv2:oid 1.3.6.1.4.1.1332.1.1.5.3.111.10.1.7;
        }
      }
    }

    container msanOnuEthPortStatTable {
            config false;

      description
       "Description.";
      smiv2:oid 1.3.6.1.4.1.1332.1.1.5.3.111.11;

      list msanOnuEthPortStatEntry {
        key "msanOnuEthPortStatOnuIfName msanOnuEthPortStatUniId msanOnuEthPortStatIntervalId";
        description
         "Description.";
        smiv2:oid 1.3.6.1.4.1.1332.1.1.5.3.111.11.1;

        leaf msanOnuEthPortStatOnuIfName {
          type if:interface-state-ref;
          description
           "Index of ONU (from ifTable).";
          smiv2:max-access not-accessible;
          smiv2:oid 1.3.6.1.4.1.1332.1.1.5.3.111.11.1.1;
        }

        leaf msanOnuEthPortStatUniId {
          type int32;
          description
           "ONU Ethernet Port (UNI) identifier.";
          smiv2:max-access not-accessible;
          smiv2:oid 1.3.6.1.4.1.1332.1.1.5.3.111.11.1.2;
        }

        leaf msanOnuEthPortStatIntervalId {
          type int32 {
            range "0..96";
          }
          description
           "Serves as an index for this table. Identifies the
            15 interval in which PM was collected. The value
            0 identifies the current interval. Value 1 identifies
            the latest 15 minute interval and value 96
            identifies the last 15 minute interval in a a 24 hour period.";
          smiv2:max-access not-accessible;
          smiv2:oid 1.3.6.1.4.1.1332.1.1.5.3.111.11.1.3;
        }

        leaf msanOnuEthPortStatInPkts {
          type yang:counter64;
          units Packets;
          description
           "The total number of received ethernet packets.";
          smiv2:max-access read-only;
          smiv2:oid 1.3.6.1.4.1.1332.1.1.5.3.111.11.1.4;
        }

        leaf msanOnuEthPortStatInUcastPkts {
          type yang:counter64;
          units Packets;
          description
           "The number of received unicast ethernet packets.";
          smiv2:max-access read-only;
          smiv2:oid 1.3.6.1.4.1.1332.1.1.5.3.111.11.1.5;
        }

        leaf msanOnuEthPortStatInMcastPkts {
          type yang:counter64;
          units Packets;
          description
           "The number of received multicast ethernet packets.";
          smiv2:max-access read-only;
          smiv2:oid 1.3.6.1.4.1.1332.1.1.5.3.111.11.1.6;
        }

        leaf msanOnuEthPortStatInBcastPkts {
          type yang:counter64;
          units Packets;
          description
           "The number of received broadcast ethernet packets.";
          smiv2:max-access read-only;
          smiv2:oid 1.3.6.1.4.1.1332.1.1.5.3.111.11.1.7;
        }

        leaf msanOnuEthPortStatInOctets {
          type yang:counter64;
          units Octets;
          description
           "The total number of octets received on the interface,
            including framing characters.";
          smiv2:max-access read-only;
          smiv2:oid 1.3.6.1.4.1.1332.1.1.5.3.111.11.1.8;
        }

        leaf msanOnuEthPortStatInPkts64Octets {
          type yang:counter64;
          units Packets;
          description
           "The number of received packets (including bad packets)
            that were 64 octets long, excluding framing bitsbut including FCS.";
          smiv2:max-access read-only;
          smiv2:oid 1.3.6.1.4.1.1332.1.1.5.3.111.11.1.9;
        }

        leaf msanOnuEthPortStatInPkts64to127Octets {
          type yang:counter64;
          units Packets;
          description
           "The number of received packets (including bad packets)
            that were 65..127 octets long,
            excluding framing bits but including FCS. ";
          smiv2:max-access read-only;
          smiv2:oid 1.3.6.1.4.1.1332.1.1.5.3.111.11.1.10;
        }

        leaf msanOnuEthPortStatInPkts128to255Octets {
          type yang:counter64;
          units Packets;
          description
           "The number of received ethernet packets that were between 128 and 255 octets in length.";
          smiv2:max-access read-only;
          smiv2:oid 1.3.6.1.4.1.1332.1.1.5.3.111.11.1.11;
        }

        leaf msanOnuEthPortStatInPkts256to511Octets {
          type yang:counter64;
          units Packets;
          description
           "The number of received ethernet packets that were between 256 and 511 octets in length.";
          smiv2:max-access read-only;
          smiv2:oid 1.3.6.1.4.1.1332.1.1.5.3.111.11.1.12;
        }

        leaf msanOnuEthPortStatInPkts512to1023Octets {
          type yang:counter64;
          units Packets;
          description
           "The number of received ethernet packets that were between 256 and 511 octets in length.";
          smiv2:max-access read-only;
          smiv2:oid 1.3.6.1.4.1.1332.1.1.5.3.111.11.1.13;
        }

        leaf msanOnuEthPortStatInPkts1024to1518Octets {
          type yang:counter64;
          units Packets;
          description
           "The number of received ethernet packets that were between 512 and 1518 octets in length.";
          smiv2:max-access read-only;
          smiv2:oid 1.3.6.1.4.1.1332.1.1.5.3.111.11.1.14;
        }

        leaf msanOnuEthPortStatInDiscards {
          type yang:counter64;
          units Packets;
          description
           "The number of discarded received ethernet packets.";
          smiv2:max-access read-only;
          smiv2:oid 1.3.6.1.4.1.1332.1.1.5.3.111.11.1.15;
        }

        leaf msanOnuEthPortStatInUndersizePkts {
          type yang:counter64;
          units Packets;
          description
           "The number of packets received that were
            less than 64 octets long  and were otherwise well
            formed.";
          smiv2:max-access read-only;
          smiv2:oid 1.3.6.1.4.1.1332.1.1.5.3.111.11.1.16;
        }

        leaf msanOnuEthPortStatInOversizePkts {
          type yang:counter64;
          units Packets;
          description
           "The total number of packets received that were
            longer than 1518 octets (excluding framing bits,
            but including FCS octets) and were otherwise
            well formed.";
          smiv2:max-access read-only;
          smiv2:oid 1.3.6.1.4.1.1332.1.1.5.3.111.11.1.17;
        }

        leaf msanOnuEthPortStatInFragments {
          type yang:counter64;
          units Packets;
          description
           "The number of packets received that were less than
            64 octets long, excluding framing
            bits but including FCS octets, and had either a bad
            Packet check sequence (FCS) with an integral
            number of octets (FCS error) or a bad FCS with a non-integral
            number of octets (alignment error).
            It is entirely normal for this attribute to increment.
            This is because it counts both runts (which are normal
            occurrences due to collisions) and noise hits. ";
          smiv2:max-access read-only;
          smiv2:oid 1.3.6.1.4.1.1332.1.1.5.3.111.11.1.18;
        }

        leaf msanOnuEthPortStatInJabbers {
          type yang:counter64;
          units Packets;
          description
           "The number of packets received that were longer than
            1518 octets, excluding framing bits but including FCS octets,
            and had either a bad Packet check sequence (FCS) with an integral
            number of octets (FCS error) or a bad FCS with a non-integral
            number of octets (alignment error).
            The range to detect jabber is between 20 ms and 150 ms.";
          smiv2:max-access read-only;
          smiv2:oid 1.3.6.1.4.1.1332.1.1.5.3.111.11.1.19;
        }

        leaf msanOnuEthPortStatInFcsErrors {
          type yang:counter64;
          units Packets;
          description
           "The number of received ethernet packets with FCS error.";
          smiv2:max-access read-only;
          smiv2:oid 1.3.6.1.4.1.1332.1.1.5.3.111.11.1.20;
        }

        leaf msanOnuEthPortStatInBufferOverflows {
          type yang:counter64;
          units Packets;
          description
           "This attribute counts the number of times that
            the receive buffer overflowed.";
          smiv2:max-access read-only;
          smiv2:oid 1.3.6.1.4.1.1332.1.1.5.3.111.11.1.21;
        }

        leaf msanOnuEthPortStatInAlignmentError {
          type yang:counter64;
          units Packets;
          description
           "This attribute counts received Packets that were
            not an integral number of octets in length
            and did not pass the FCS check.";
          smiv2:max-access read-only;
          smiv2:oid 1.3.6.1.4.1.1332.1.1.5.3.111.11.1.22;
        }

        leaf msanOnuEthPortStatInInternalMACReceiveError {
          type yang:counter64;
          units Packets;
          description
           "This attribute counts Packets whose reception
            failed due to an internal MAC sublayer receive error ";
          smiv2:max-access read-only;
          smiv2:oid 1.3.6.1.4.1.1332.1.1.5.3.111.11.1.23;
        }

        leaf msanOnuEthPortStatOutPkts {
          type yang:counter64;
          units Packets;
          description
           "The total number of transmitted ethernet packets.";
          smiv2:max-access read-only;
          smiv2:oid 1.3.6.1.4.1.1332.1.1.5.3.111.11.1.24;
        }

        leaf msanOnuEthPortStatOutUcastPkts {
          type yang:counter64;
          units Packets;
          description
           "The number of transmitted unicast ethernet packets.";
          smiv2:max-access read-only;
          smiv2:oid 1.3.6.1.4.1.1332.1.1.5.3.111.11.1.25;
        }

        leaf msanOnuEthPortStatOutMcastPkts {
          type yang:counter64;
          units Packets;
          description
           "The number of transmitted multicast ethernet packets.";
          smiv2:max-access read-only;
          smiv2:oid 1.3.6.1.4.1.1332.1.1.5.3.111.11.1.26;
        }

        leaf msanOnuEthPortStatOutBcastPkts {
          type yang:counter64;
          units Packets;
          description
           "The number of transmitted broadcast ethernet packets.";
          smiv2:max-access read-only;
          smiv2:oid 1.3.6.1.4.1.1332.1.1.5.3.111.11.1.27;
        }

        leaf msanOnuEthPortStatOutDiscards {
          type yang:counter64;
          units Packets;
          description
           "The number of discarded transmitted ethernet packets.";
          smiv2:max-access read-only;
          smiv2:oid 1.3.6.1.4.1.1332.1.1.5.3.111.11.1.28;
        }

        leaf msanOnuEthPortStatOutFcsErrors {
          type yang:counter64;
          units Packets;
          description
           "The number of transmitted ethernet packets with FCS error.";
          smiv2:max-access read-only;
          smiv2:oid 1.3.6.1.4.1.1332.1.1.5.3.111.11.1.29;
        }

        leaf msanOnuEthPortStatOutExcessiveCollisions {
          type yang:counter64;
          units Packets;
          description
           "This attribute counts Packets whose transmission
            failed due to excessive collisions. ";
          smiv2:max-access read-only;
          smiv2:oid 1.3.6.1.4.1.1332.1.1.5.3.111.11.1.30;
        }

        leaf msanOnuEthPortStatOutLateCollisions {
          type yang:counter64;
          units Packets;
          description
           "This attribute counts the number of times that
            a collision was detected later than 512 bit
            times into the transmission of a packet.";
          smiv2:max-access read-only;
          smiv2:oid 1.3.6.1.4.1.1332.1.1.5.3.111.11.1.31;
        }

        leaf msanOnuEthPortStatOutBufferOverflows {
          type yang:counter64;
          units Packets;
          description
           "This attribute counts the number of times that
            the transmit buffer overflowed.";
          smiv2:max-access read-only;
          smiv2:oid 1.3.6.1.4.1.1332.1.1.5.3.111.11.1.32;
        }

        leaf msanOnuEthPortStatOutSingleCollisionPkts {
          type yang:counter64;
          units Packets;
          description
           "This attribute counts successfully transmitted
            Packets whose transmission was delayed by
            exactly one collision. ";
          smiv2:max-access read-only;
          smiv2:oid 1.3.6.1.4.1.1332.1.1.5.3.111.11.1.33;
        }

        leaf msanOnuEthPortStatOutMultipleCollisionsPkts {
          type yang:counter64;
          units Packets;
          description
           "This attribute counts successfully transmitted
            Packets whose transmission was delayed by
            more than one collision.";
          smiv2:max-access read-only;
          smiv2:oid 1.3.6.1.4.1.1332.1.1.5.3.111.11.1.34;
        }

        leaf msanOnuEthPortStatOutDeferredTransmission {
          type yang:counter64;
          units Packets;
          description
           "This attribute counts Packets whose first
            transmission attempt was delayed because the medium
            was busy. The count does not include Packets
            involved in collisions.";
          smiv2:max-access read-only;
          smiv2:oid 1.3.6.1.4.1.1332.1.1.5.3.111.11.1.35;
        }

        leaf msanOnuEthPortStatOutInternalMACTransmitError {
          type yang:counter64;
          units Packets;
          description
           "This attribute counts Packets whose transmission
            failed due to an internal MAC sublayer transmit error.";
          smiv2:max-access read-only;
          smiv2:oid 1.3.6.1.4.1.1332.1.1.5.3.111.11.1.36;
        }

        leaf msanOnuEthPortStatSQEs {
          type yang:counter64;
          description
           "This attribute counts the number of times that
            the SQE test error message was generated by
            the PLS sublayer.";
          smiv2:max-access read-only;
          smiv2:oid 1.3.6.1.4.1.1332.1.1.5.3.111.11.1.37;
        }

        leaf msanOnuEthPortStatCarrierSenseError {
          type yang:counter64;
          description
           "This attribute counts the number of times that
            carrier sense was lost or never asserted when
            attempting to transmit a Packet.";
          smiv2:max-access read-only;
          smiv2:oid 1.3.6.1.4.1.1332.1.1.5.3.111.11.1.38;
        }
      }
    }

    container msanOnuDefaultConfigFileTable {
      description
       "Description.";
      smiv2:oid 1.3.6.1.4.1.1332.1.1.5.3.111.12;

      list msanOnuDefaultConfigFileEntry {
        key msanOnuDefaultConfigFileName;
        description
         "Description.";
        smiv2:oid 1.3.6.1.4.1.1332.1.1.5.3.111.12.1;

        leaf msanOnuDefaultConfigFileName {
          type rfc1213-mib:DisplayString;
          description
           "ONU default config file name.";
          smiv2:max-access not-accessible;
          smiv2:oid 1.3.6.1.4.1.1332.1.1.5.3.111.12.1.1;
        }
      }
    }

    container msanOnuCfgAttributeTable {
      description
       "Description.";
      smiv2:oid 1.3.6.1.4.1.1332.1.1.5.3.111.13;

      list msanOnuCfgAttributeEntry {
        key "msanOnuCfgAttributeIfName msanOnuCfgAttributeId";
        description
         "Supported management methods:
          - DELETE all attributes for selected ONU (msanOnuCfgAttributeIfIndex)
          - ADD attribute for selected ONU where msanOnuCfgAttributeId must be set to 0.";
        smiv2:oid 1.3.6.1.4.1.1332.1.1.5.3.111.13.1;

        leaf msanOnuCfgAttributeIfName {
          type if:interface-ref;
          description
           "ONU interface name.";
          smiv2:max-access not-accessible;
          smiv2:oid 1.3.6.1.4.1.1332.1.1.5.3.111.13.1.1;
        }
                leaf msanOnuCfgAttributeId {
                    type int32;
                    description "Onu Attribute Id";
                }


        leaf msanOnuCfgAttributeName {
          type rfc1213-mib:DisplayString;
          description
           "ONU config attribute name.";
          smiv2:max-access not-accessible;
          smiv2:oid 1.3.6.1.4.1.1332.1.1.5.3.111.13.1.1;
        }

        leaf msanOnuCfgAttributeValue {
          type rfc1213-mib:DisplayString;
          description
           "ONU config attribute value";
          smiv2:max-access not-accessible;
          smiv2:oid 1.3.6.1.4.1.1332.1.1.5.3.111.13.1.2;
        }
      }
    }

container msanOnuVideoAniPortTable {
      description
       "Description.";
      smiv2:oid 1.3.6.1.4.1.1332.1.1.5.3.111.14;

      list msanOnuVideoAniPortEntry {
        key "msanOnuVideoAniPortOnuIfName msanOnuVideoAniPortAniId";
        description
         "Description.";
        smiv2:oid 1.3.6.1.4.1.1332.1.1.5.3.111.14.1;

        leaf msanOnuVideoAniPortOnuIfName {
          type if:interface-ref;
          description
           "ONU interface name.";
          smiv2:max-access not-accessible;
          smiv2:oid 1.3.6.1.4.1.1332.1.1.5.3.111.14.1.1;
        }

        leaf msanOnuVideoAniPortAniId {
          type int32;
          description
           "ONU Video ANI Port identifier.";
          smiv2:max-access not-accessible;
          smiv2:oid 1.3.6.1.4.1.1332.1.1.5.3.111.14.1.2;
        }

        leaf msanOnuVideoAniPortAdminState {
          type enumeration {
            enum enable {
              value 1;
            }
            enum disable {
              value 2;
            }
          }
                    config false;

          description
           "ONU Video ANI port  administration state.";
          smiv2:max-access read-write;
          smiv2:oid 1.3.6.1.4.1.1332.1.1.5.3.111.14.1.3;
        }

        leaf msanOnuVideoAniPortOperState {
          type enumeration {
            enum up {
              value 1;
            }
            enum down {
              value 2;
            }
            enum notAvailable {
              value 3;
            }
          }
                    config false;

          description
           "ONU Video ANI port  operational state.";
          smiv2:max-access read-only;
          smiv2:oid 1.3.6.1.4.1.1332.1.1.5.3.111.14.1.4;
        }

        leaf msanOnuVideoAniPortTotalOpticalPowerLevel {
          type int32 ;
                    config false;

          description
           "ONU Video ANI port  Total Optical Power Level [dBuW].
            Info: -1 defines that value is not available.";
          smiv2:max-access read-only;
        }
      }
    }

    container msanOnuVideoUniPortTable {
      description
       "Description.";
      smiv2:oid 1.3.6.1.4.1.1332.1.1.5.3.111.15;

      list msanOnuVideoUniPortEntry {
        key "msanOnuVideoUniPortOnuIfName msanOnuVideoUniPortUniId";
        description
         "Description.";
        smiv2:oid 1.3.6.1.4.1.1332.1.1.5.3.111.15.1;

        leaf msanOnuVideoUniPortOnuIfName {
          type if:interface-ref;
          description
           "ONU interface name.";
          smiv2:max-access not-accessible;
          smiv2:oid 1.3.6.1.4.1.1332.1.1.5.3.111.15.1.1;
        }

        leaf msanOnuVideoUniPortUniId {
          type int32;
          description
           "ONU Video Ani Port identifier.";
          smiv2:max-access not-accessible;
          smiv2:oid 1.3.6.1.4.1.1332.1.1.5.3.111.15.1.2;
        }

        leaf msanOnuVideoUniPortAdminState {
          type enumeration {
            enum enable {
              value 1;
            }
            enum disable {
              value 2;
            }
          }
                    config false;

          description
           "ONU Video UNI port  administration state.";
          smiv2:max-access read-write;
          smiv2:oid 1.3.6.1.4.1.1332.1.1.5.3.111.15.1.3;
        }

        leaf msanOnuVideoUniPortOperState {
          type enumeration {
            enum up {
              value 1;
            }
            enum down {
              value 2;
            }
            enum notAvailable {
              value 3;
            }
          }
                    config false;

          description
           "ONU Video UNI port  operational state.";
          smiv2:max-access read-only;
          smiv2:oid 1.3.6.1.4.1.1332.1.1.5.3.111.15.1.4;
        }
      }
    }

    container msanOltPortTable {
      description
       " ";
      smiv2:oid 1.3.6.1.4.1.1332.1.1.5.3.112.2;

      list msanOltPortEntry {
        key msanOltPortIfName;
        description
         "Row Description";
        smiv2:oid 1.3.6.1.4.1.1332.1.1.5.3.112.2.1;

        leaf msanOltPortIfName {
          type if:interface-ref;
          description
           "Index of OLT port (from ifTable).";
          smiv2:max-access not-accessible;
          smiv2:oid 1.3.6.1.4.1.1332.1.1.5.3.112.2.1.2;
        }

        leaf msanOltPortOnuDiscoveryMode {
          type enumeration {
            enum autoPeriodic {
              value 1;
            }
            enum manualEnabledOnceThenDisabled {
              value 2;
            }
            enum disabled {
              value 3;
            }
          }
          description
           "ONU discovery mode:
            1 Auto periodic (onuDiscoveryInterval is the
            period)
            2 Manual enabled once then disabled
            3 Disabled ";
          smiv2:defval autoPeriodic;
          smiv2:max-access read-write;
          smiv2:oid 1.3.6.1.4.1.1332.1.1.5.3.112.2.1.5;
        }

        leaf msanOltPortOnuDiscoveryInterval {
          type uint32 {
            range "1..3600";
          }
          description
           "ONU discovery interval, i.e., serial Number acquisition
            interval in seconds. The value ranges from 1 to 3600 ";
          smiv2:defval 30;
          smiv2:max-access read-write;
          smiv2:oid 1.3.6.1.4.1.1332.1.1.5.3.112.2.1.6;
        }

        leaf msanOltPortDbaCycleTime {
          type uint32 {
            range "2..8";
          }
          description
           "Upstream bandwidth assignment cycle time. only support 2ms, 4ms and 8ms.";
          smiv2:defval 8;
          smiv2:max-access read-write;
          smiv2:oid 1.3.6.1.4.1.1332.1.1.5.3.112.2.1.7;
        }

        leaf msanOltPortLinkMinDistance {
          type int32 {
            range "0..60";
          }
          units km;
          description
           "Minimum PON link distance.
            
            Maximum allowed interval between msanOltPortLinkMinDistance and msanOltPortLinkMaxDistance
            is 20km.";
          smiv2:max-access read-write;
          smiv2:oid 1.3.6.1.4.1.1332.1.1.5.3.112.2.1.8;
        }

        leaf msanOltPortLinkMaxDistance {
          type int32 {
            range "0..60";
          }
          units km;
          description
           "Maximum PON link distance.
            
            Maximum allowed interval between msanOltPortLinkMinDistance and msanOltPortLinkMaxDistance
            is 20km.";
          smiv2:max-access read-write;
          smiv2:oid 1.3.6.1.4.1.1332.1.1.5.3.112.2.1.9;
        }

        leaf msanOltPortLosThreshold {
          type int32 {
            range "1..10";
          }
                    config false;

          description
           "The number of consecutive upstream frames that had valid alloc id for which no optical signal was received from
            any ONT on the link. After this many number of frames, a LOS alarm will be raised.
            WARNING: The default value = 4 is set by G984.3 Standard. Modify for debug purposes only.";
          smiv2:defval 4;
          smiv2:max-access read-only;
          smiv2:oid 1.3.6.1.4.1.1332.1.1.5.3.112.2.1.10;
        }

        leaf msanOltPortLofThreshold {
          type int32 {
            range "1..10";
          }
                    config false;

          description
           "The number of consecutive upstream frames from an ONT that are lost. After this many number of frames, a LOFi
            alarm will be raised.
            WARNING: The default value = 4 is set by G984.3 Standard. Modify for debug purposes only.";
          smiv2:defval 4;
          smiv2:max-access read-only;
          smiv2:oid 1.3.6.1.4.1.1332.1.1.5.3.112.2.1.11;
        }

        leaf msanOltPortBlackListRefresh {
          type enumeration {
            enum enable {
              value 1;
            }
            enum disable {
              value 2;
            }
          }
          description
           "Set this option to �enable�to initiate a blacklist refresh for this OLT port.";
          smiv2:max-access read-write;
          smiv2:oid 1.3.6.1.4.1.1332.1.1.5.3.112.2.1.12;
        }

        leaf msanOltPortUsEstAvailTotalBw {
          type int32;
          units kbps;
                    config false;

          description
           "OLT interface estimated available total upstream bandwidth.";
          smiv2:max-access read-only;
          smiv2:oid 1.3.6.1.4.1.1332.1.1.5.3.112.2.1.13;
        }

        leaf msanOltPortUsEstAvailFixedBw {
          type int32;
          units kbps;
                    config false;

          description
           "OLT interface estimated available fixed upstream bandwidth.";
          smiv2:max-access read-only;
          smiv2:oid 1.3.6.1.4.1.1332.1.1.5.3.112.2.1.14;
        }

        leaf msanOltPortUsActAvailTotalBw {
          type int32;
          units kbps;
                    config false;

          description
           "OLT interface actual available total upstream bandwidth.";
          smiv2:max-access read-only;
          smiv2:oid 1.3.6.1.4.1.1332.1.1.5.3.112.2.1.15;
        }

        leaf msanOltPortUsActAvailFixedBw {
          type int32;
          units kbps;
                    config false;

          description
           "OLT interface actual available total upstream bandwidth.";
          smiv2:max-access read-only;
          smiv2:oid 1.3.6.1.4.1.1332.1.1.5.3.112.2.1.16;
        }

        leaf msanOltPortEncryptKeyExchange {
          type enumeration {
            enum enable {
              value 1;
            }
            enum disable {
              value 2;
            }
          }
          description
           "Encryption key exchange.";
          smiv2:max-access read-write;
          smiv2:oid 1.3.6.1.4.1.1332.1.1.5.3.112.2.1.17;
        }

        leaf msanOltPortEncryptKeyExchangeInterval {
          type int32 {
            range "30..26000";
          }
          units seconds;
          description
           "Encryption key exchange interval.";
          smiv2:max-access read-write;
          smiv2:oid 1.3.6.1.4.1.1332.1.1.5.3.112.2.1.18;
        }
                leaf msanOltPortTransciverVendorPN {
                    type rfc1213-mib:DisplayString;
                    description 
                        "GPON SFP type
                         ";
                }
                leaf msanOltPortRogueOnuDetection {

          type enumeration {
            enum enable {
              value 1;
            }
            enum disable {
              value 2;
            }
          }
          description
           "Rogue ONU detection.
            ";                }
                leaf msanOltPortOnuPhyPowerLevel {

          type enumeration {
            enum normal {
              value 1;
            }
            enum level3dB {
              value 2;
            }
            enum level6dB {
              value 3;
            }
          }
          description
           "ONU phy power leveling
            ";                }

      }
    }

    container msanOltPortStatTable {
            config false;

      description
       "Description.";
      smiv2:oid 1.3.6.1.4.1.1332.1.1.5.3.112.3;

      list msanOltPortStatEntry {
        key "msanOltPortStatIfName msanOltPortStatIntervalId";
        description
         "Description.";
        smiv2:oid 1.3.6.1.4.1.1332.1.1.5.3.112.3.1;

        leaf msanOltPortStatIfName {
          type if:interface-state-ref;
          description
           "Name of OLT interface.";
          smiv2:max-access not-accessible;
          smiv2:oid 1.3.6.1.4.1.1332.1.1.5.3.112.3.1.1;
        }

        leaf msanOltPortStatIntervalId {
          type int32 {
            range "0..96";
          }
          description
           "Serves as an index for this table. Identifies the
            15 interval in which PM was collected. The value
            0 identifies the current interval. Value 1 identifies
            the latest 15 minute interval and value 96
            identifies the last 15 minute interval in a a 24 hour period.";
          smiv2:max-access not-accessible;
          smiv2:oid 1.3.6.1.4.1.1332.1.1.5.3.112.3.1.2;
        }

        leaf msanOltPortStatInOmciPkts {
          type yang:counter64;
          units Packets;
          description
           "Received OMCI packets.";
          smiv2:max-access read-only;
          smiv2:oid 1.3.6.1.4.1.1332.1.1.5.3.112.3.1.3;
        }

        leaf msanOltPortStatInCpuPkts {
          type yang:counter64;
          units Packets;
          description
           "Received CPU packets.";
          smiv2:max-access read-only;
          smiv2:oid 1.3.6.1.4.1.1332.1.1.5.3.112.3.1.4;
        }

        leaf msanOltPortStatInDiscardedPkts {
          type yang:counter64;
          units Packets;
          description
           "Number of dropped received packets.";
          smiv2:max-access read-only;
          smiv2:oid 1.3.6.1.4.1.1332.1.1.5.3.112.3.1.5;
        }

        leaf msanOltPortStatInUndersizePkts {
          type yang:counter64;
          units Packets;
          description
           "Received packets dropped due to length too short.";
          smiv2:max-access read-only;
          smiv2:oid 1.3.6.1.4.1.1332.1.1.5.3.112.3.1.6;
        }

        leaf msanOltPortStatInOversizePkts {
          type yang:counter64;
          units Packets;
          description
           "Received packets dropped due to length too long.";
          smiv2:max-access read-only;
          smiv2:oid 1.3.6.1.4.1.1332.1.1.5.3.112.3.1.7;
        }

        leaf msanOltPortStatInCrcErrorPkts {
          type yang:counter64;
          units Packets;
          description
           "Received packets dropped due to CRC error.";
          smiv2:max-access read-only;
          smiv2:oid 1.3.6.1.4.1.1332.1.1.5.3.112.3.1.8;
        }

        leaf msanOltPortStatInKeyErrorPkts {
          type yang:counter64;
          units Packets;
          description
           "Received packets dropped due to Key error.";
          smiv2:max-access read-only;
          smiv2:oid 1.3.6.1.4.1.1332.1.1.5.3.112.3.1.9;
        }

        leaf msanOltPortStatInTpidErrorPkts {
          type yang:counter64;
          units Packets;
          description
           "Received packet dropped due to TPID error.";
          smiv2:max-access read-only;
          smiv2:oid 1.3.6.1.4.1.1332.1.1.5.3.112.3.1.10;
        }

        leaf msanOltPortStatInVidErrorPkts {
          type yang:counter64;
          units Packets;
          description
           "Received packet dropped due to VID error.";
          smiv2:max-access read-only;
          smiv2:oid 1.3.6.1.4.1.1332.1.1.5.3.112.3.1.11;
        }

        leaf msanOltPortStatInFragmentErrorPkts {
          type yang:counter64;
          units Packets;
          description
           "Received packet dropped due to fragmentation error.";
          smiv2:max-access read-only;
          smiv2:oid 1.3.6.1.4.1.1332.1.1.5.3.112.3.1.12;
        }

        leaf msanOltPortStatInGemFrames {
          type yang:counter64;
          units Frames;
          description
           "Received GEM frames.";
          smiv2:max-access read-only;
          smiv2:oid 1.3.6.1.4.1.1332.1.1.5.3.112.3.1.13;
        }

        leaf msanOltPortStatInDiscardedGemFrames {
          type yang:counter64;
          units Frames;
          description
           "Number of corrected received GEM frames.";
          smiv2:max-access read-only;
          smiv2:oid 1.3.6.1.4.1.1332.1.1.5.3.112.3.1.14;
        }

        leaf msanOltPortStatInIdleGemFrames {
          type yang:counter64;
          units Frames;
          description
           "Number of idle received GEM frames.";
          smiv2:max-access read-only;
          smiv2:oid 1.3.6.1.4.1.1332.1.1.5.3.112.3.1.15;
        }

        leaf msanOltPortStatInCorrectedGemFrames {
          type yang:counter64;
          units Frames;
          description
           "Number of corrected received GEM frames.";
          smiv2:max-access read-only;
          smiv2:oid 1.3.6.1.4.1.1332.1.1.5.3.112.3.1.16;
        }

        leaf msanOltPortStatInIllegalGemFrames {
          type yang:counter64;
          units Frames;
          description
           "Number of illegal received GEM frames.";
          smiv2:max-access read-only;
          smiv2:oid 1.3.6.1.4.1.1332.1.1.5.3.112.3.1.17;
        }

        leaf msanOltPortStatInValidAllocations {
          type yang:counter64;
          units Allocations;
          description
           "Number of received valid allocations.";
          smiv2:max-access read-only;
          smiv2:oid 1.3.6.1.4.1.1332.1.1.5.3.112.3.1.18;
        }

        leaf msanOltPortStatInInvalidAllocations {
          type yang:counter64;
          units Allocations;
          description
           "Number of received invalid allocations.";
          smiv2:max-access read-only;
          smiv2:oid 1.3.6.1.4.1.1332.1.1.5.3.112.3.1.19;
        }

        leaf msanOltPortStatInDisabledAllocations {
          type yang:counter64;
          units Allocations;
          description
           "Number of received disabled allocations.";
          smiv2:max-access read-only;
          smiv2:oid 1.3.6.1.4.1.1332.1.1.5.3.112.3.1.20;
        }

        leaf msanOltPortStatInPloamMsgs {
          type yang:counter64;
          units "PLOAM messages";
          description
           "Number of received PLOAM (physical layer operations and maintenance) messages.";
          smiv2:max-access read-only;
          smiv2:oid 1.3.6.1.4.1.1332.1.1.5.3.112.3.1.21;
        }

        leaf msanOltPortStatInNonIdlePloamMsgs {
          type yang:counter64;
          units Messages;
          description
           "Number of received non-idle PLOAM (physical layer operations and maintenance) messages.";
          smiv2:max-access read-only;
          smiv2:oid 1.3.6.1.4.1.1332.1.1.5.3.112.3.1.22;
        }

        leaf msanOltPortStatInErrorPloamMsgs {
          type yang:counter64;
          units Messages;
          description
           "Number of received PLOAM (physical layer operations and maintenance) messages with errors.";
          smiv2:max-access read-only;
          smiv2:oid 1.3.6.1.4.1.1332.1.1.5.3.112.3.1.23;
        }

        leaf msanOltPortStatInDiscardedPloamMsgs {
          type yang:counter64;
          units Messages;
          description
           "Number of discarded PLOAM (physical layer operations and maintenance) messages.";
          smiv2:max-access read-only;
          smiv2:oid 1.3.6.1.4.1.1332.1.1.5.3.112.3.1.24;
        }

        leaf msanOltPortStatInFecCodewords {
          type yang:counter64;
          description
           "Number of received FEC (Forward error correction) codewords.";
          smiv2:max-access read-only;
          smiv2:oid 1.3.6.1.4.1.1332.1.1.5.3.112.3.1.25;
        }

        leaf msanOltPortStatInUncorrectedFecCodewords {
          type yang:counter64;
          description
           "Number of received uncorrected FEC (Forward error correction) codewords.";
          smiv2:max-access read-only;
          smiv2:oid 1.3.6.1.4.1.1332.1.1.5.3.112.3.1.26;
        }

        leaf msanOltPortStatInBip8ProtectedBytes {
          type yang:counter64;
          units Bytes;
          description
           "Number of received bytes protected by Bip8.";
          smiv2:max-access read-only;
          smiv2:oid 1.3.6.1.4.1.1332.1.1.5.3.112.3.1.27;
        }

        leaf msanOltPortStatInBip8ErrorBytes {
          type yang:counter64;
          units Bytes;
          description
           "Number of received bytes with Bip8 error.";
          smiv2:max-access read-only;
          smiv2:oid 1.3.6.1.4.1.1332.1.1.5.3.112.3.1.28;
        }

        leaf msanOltPortStatOutOmciPkts {
          type yang:counter64;
          units Packets;
          description
           "Transmitted OMCI packets.";
          smiv2:max-access read-only;
          smiv2:oid 1.3.6.1.4.1.1332.1.1.5.3.112.3.1.29;
        }

        leaf msanOltPortStatOutCpuPkts {
          type yang:counter64;
          units Packets;
          description
           "Transmitted CPU packets.";
          smiv2:max-access read-only;
          smiv2:oid 1.3.6.1.4.1.1332.1.1.5.3.112.3.1.30;
        }

        leaf msanOltPortStatOutDiscardedPkts {
          type yang:counter64;
          units Packets;
          description
           "Number of dropped transmitted packets because of illegal length.";
          smiv2:max-access read-only;
          smiv2:oid 1.3.6.1.4.1.1332.1.1.5.3.112.3.1.31;
        }

        leaf msanOltPortStatOutGemFrames {
          type yang:counter64;
          units Frames;
          description
           "Transmitted GEM frames.";
          smiv2:max-access read-only;
          smiv2:oid 1.3.6.1.4.1.1332.1.1.5.3.112.3.1.32;
        }

        leaf msanOltPortStatOutPloamMsgs {
          type yang:counter64;
          units "PLOAM messages";
          description
           "Number of transmitted PLOAM (physical layer operations and maintenance) messages.";
          smiv2:max-access read-only;
          smiv2:oid 1.3.6.1.4.1.1332.1.1.5.3.112.3.1.33;
        }
      }
    }

container msanOltOnuPortStatTable {
            config false;

      description
       "Description.";
      smiv2:oid 1.3.6.1.4.1.1332.1.1.5.3.112.4;

      list msanOltOnuPortStatEntry {
        key msanOltOnuPortStatIfName;
        description
         "Description.";
        smiv2:oid 1.3.6.1.4.1.1332.1.1.5.3.112.4.1;

        leaf msanOltOnuPortStatIfName {
          type if:interface-state-ref;
          description
           "Name of ONU interface.";
          smiv2:max-access not-accessible;
          smiv2:oid 1.3.6.1.4.1.1332.1.1.5.3.112.4.1.1;
        }

        leaf msanOltOnuPortStatInFecCodewords {
          type yang:counter64;
          units Codewords;
          description
           "Number of received FEC (Forward error correction) codewords.";
          smiv2:max-access read-only;
          smiv2:oid 1.3.6.1.4.1.1332.1.1.5.3.112.4.1.2;
        }

        leaf msanOltOnuPortStatInFecBytesCorrected {
          type yang:counter64;
          units Bytes;
          description
           "Number of received corrected FEC (Forward error correction) bytes.";
          smiv2:max-access read-only;
          smiv2:oid 1.3.6.1.4.1.1332.1.1.5.3.112.4.1.3;
        }

        leaf msanOltOnuPortStatInFecCodewordsCorrected {
          type yang:counter64;
          units Codewords;
          description
           "Number of received corrected FEC (Forward error correction) codewords.";
          smiv2:max-access read-only;
          smiv2:oid 1.3.6.1.4.1.1332.1.1.5.3.112.4.1.4;
        }

        leaf msanOltOnuPortStatInFecCodewordsUncorrected {
          type yang:counter64;
          units Codewords;
          description
           "Number of received uncorrected FEC (Forward error correction) codewords.";
          smiv2:max-access read-only;
          smiv2:oid 1.3.6.1.4.1.1332.1.1.5.3.112.4.1.5;
        }

        leaf msanOltOnuPortStatInBip8Bytes {
          type yang:counter64;
          units Bytes;
          description
           "Number of received bytes protected by Bip8.";
          smiv2:max-access read-only;
          smiv2:oid 1.3.6.1.4.1.1332.1.1.5.3.112.4.1.6;
        }

        leaf msanOltOnuPortStatInBip8Errors {
          type yang:counter64;
          description
           "Number of received  Bip8 errors.";
          smiv2:max-access read-only;
          smiv2:oid 1.3.6.1.4.1.1332.1.1.5.3.112.4.1.7;
        }

        leaf msanOltOnuPortStatInPloamMsgsCrcError {
          type yang:counter64;
          units Messages;
          description
           "Number of received PLOAM (physical layer operations and maintenance) messages with CRC error.";
          smiv2:max-access read-only;
          smiv2:oid 1.3.6.1.4.1.1332.1.1.5.3.112.4.1.8;
        }

        leaf msanOltOnuPortStatInPloamMsgsNonIdle {
          type yang:counter64;
          units Messages;
          description
           "Number of received non-idle PLOAM (physical layer operations and maintenance) messages.";
          smiv2:max-access read-only;
          smiv2:oid 1.3.6.1.4.1.1332.1.1.5.3.112.4.1.9;
        }

        leaf msanOltOnuPortStatInDriftPositive {
          type yang:counter64;
          description
           "Number of accumulated positive drift in bits.";
          smiv2:max-access read-only;
          smiv2:oid 1.3.6.1.4.1.1332.1.1.5.3.112.4.1.10;
        }

        leaf msanOltOnuPortStatInDriftNegative {
          type yang:counter64;
          description
           "Number of accumulated negative drift in bits.";
          smiv2:max-access read-only;
          smiv2:oid 1.3.6.1.4.1.1332.1.1.5.3.112.4.1.11;
        }

        leaf msanOltOnuPortStatInOmciPkts {
          type yang:counter64;
          units Packets;
          description
           "Number of received OMCI packets.";
          smiv2:max-access read-only;
          smiv2:oid 1.3.6.1.4.1.1332.1.1.5.3.112.4.1.12;
        }

        leaf msanOltOnuPortStatInOmciPktsCrcError {
          type yang:counter64;
          units Packets;
          description
           "Number of received OMCI packets with CRC error.";
          smiv2:max-access read-only;
          smiv2:oid 1.3.6.1.4.1.1332.1.1.5.3.112.4.1.13;
        }

        leaf msanOltOnuPortStatInBerReported {
          type yang:counter64;
          description
           "Accumulated REI error count reported by the ONU.";
          smiv2:max-access read-only;
          smiv2:oid 1.3.6.1.4.1.1332.1.1.5.3.112.4.1.14;
        }

        leaf msanOltOnuPortStatInLcdgErrors {
          type yang:counter64;
          description
           "Number of received LCDG errors.";
          smiv2:max-access read-only;
          smiv2:oid 1.3.6.1.4.1.1332.1.1.5.3.112.4.1.15;
        }

        leaf msanOltOnuPortStatInRdiErrors {
          type yang:counter64;
          description
           "Number of received RDI errors.";
          smiv2:max-access read-only;
          smiv2:oid 1.3.6.1.4.1.1332.1.1.5.3.112.4.1.16;
        }

        leaf msanOltOnuPortStatUnreceivedBurst {
          type yang:counter64;
          description
           "Un-received burst allocated to the ONU.";
          smiv2:max-access read-only;
          smiv2:oid 1.3.6.1.4.1.1332.1.1.5.3.112.4.1.17;
        }
      }
    }

container msanOltProtectSwitchPairTable {
      description
       "Description.";
      smiv2:oid 1.3.6.1.4.1.1332.1.1.5.3.112.5;

      list msanOltProtectSwitchPairEntry {
        key msanOltProtectSwitchPairName;
        description
         "Description.";
        smiv2:oid 1.3.6.1.4.1.1332.1.1.5.3.112.5.1;

        leaf msanOltProtectSwitchPairName {
          type rfc1213-mib:DisplayString;
          description
           "OLT Protection Switching Pair name.";
          smiv2:max-access not-accessible;
          smiv2:oid 1.3.6.1.4.1.1332.1.1.5.3.112.5.1.1;
        }

        leaf msanOltProtectSwitchPairPrimaryIfIndex {
          type int32;
          description
           "OLT Protection Switching Pair: Index of Primary OLT interface  (from ifTable).
            
            Value 0 defines that parameter is not set.";
          smiv2:max-access read-write;
          smiv2:oid 1.3.6.1.4.1.1332.1.1.5.3.112.5.1.2;
        }

        leaf msanOltProtectSwitchPairPrimaryIpAddress {
          type inet:ipv4-address;
          description
           "OLT Protection Switching Pair: IP Address of Primary OLT interface.";
          smiv2:max-access read-write;
          smiv2:oid 1.3.6.1.4.1.1332.1.1.5.3.112.5.1.3;
        }

        leaf msanOltProtectSwitchPairSecondaryIfIndex {
          type int32;
          description
           "OLT Protection Switching Pair: Index of Secondary OLT interface  (from ifTable).
            
            Value 0 defines that parameter is not set.";
          smiv2:max-access read-write;
          smiv2:oid 1.3.6.1.4.1.1332.1.1.5.3.112.5.1.4;
        }

        leaf msanOltProtectSwitchPairSecondaryIpAddress {
          type inet:ipv4-address;
          description
           "OLT Protection Switching Pair: IP Address of Secondary OLT interface ";
          smiv2:max-access read-write;
          smiv2:oid 1.3.6.1.4.1.1332.1.1.5.3.112.5.1.5;
        }
                leaf msanOltProtectSwitchPairType {
                    type enumeration {
                        enum b {
                            value 1;
                        }
                    }
                    config false;
                    description "OLT Protection Switching Pair type";
                }


        leaf msanOltProtectSwitchPairTimeout {
          type int32;
          units miliseconds;
                    config false;

          description
           "OLT Protection Switching Pair connection timeout.";
          smiv2:max-access read-only;
          smiv2:oid 1.3.6.1.4.1.1332.1.1.5.3.112.5.1.7;
        }

        leaf msanOltProtectSwitchPairActive {
          type enumeration {
            enum primary {
              value 1;
            }
            enum secondary {
              value 2;
            }
                        enum none {
                            value 3;
                        }

          }
                    config false;

          description
           "OLT Protection Switching Pair currently active side.";
          smiv2:max-access read-only;
          smiv2:oid 1.3.6.1.4.1.1332.1.1.5.3.112.5.1.8;
        }

        leaf msanOltProtectSwitchPairStatus {
          type enumeration {
            enum active {
              value 1;
            }
            enum notInService {
              value 2;
            }
          }
                    config false;

          description
           "OLT Protection Switching Pair connection status.";
          smiv2:max-access read-only;
          smiv2:oid 1.3.6.1.4.1.1332.1.1.5.3.112.5.1.9;
        }

        leaf msanOltProtectSwitchPairSwitchOver {
          type enumeration {
            enum enable {
              value 1;
            }
            enum disable {
              value 2;
            }
          }
          description
           "OLT Protection Switching Pair switch over action.";
          smiv2:defval disable;
          smiv2:max-access read-write;
          smiv2:oid 1.3.6.1.4.1.1332.1.1.5.3.112.5.1.10;
        }
      }
    }

    container msanTacacsServerTable {
      description
       "Table with information about Radius Authentication Server IP
        Addresses, port numbers and shared secret";
      smiv2:oid 1.3.6.1.4.1.1332.1.1.5.3.113.2;

      list msanTacacsServerEntry {
        key msanTacacsServerIpAddress;
        description
         "Entry consisting of configuration data for a Radius
          Authentication Server.";
        smiv2:oid 1.3.6.1.4.1.1332.1.1.5.3.113.2.1;

        leaf msanTacacsServerIpAddress {
          type inet:ipv4-address;
          description
           "IP Address of the configured TACACS server.
            This object cannot be changed after creation.";
          smiv2:max-access not-accessible;
          smiv2:oid 1.3.6.1.4.1.1332.1.1.5.3.113.2.1.1;
        }

        leaf msanTacacsServerPort {
          type uint32 {
            range "0..65535";
          }
          description
           "TCP/UDP port number of the TACACS server.";
          smiv2:defval 49;
          smiv2:max-access read-write;
          smiv2:oid 1.3.6.1.4.1.1332.1.1.5.3.113.2.1.2;
        }

        leaf msanTacacsServerSecret {
          type rfc1213-mib:DisplayString {
            length "0..16";
          }
          description
           "Configured shared secret for the TACACS server.";
          smiv2:defval "";
          smiv2:max-access read-write;
          smiv2:oid 1.3.6.1.4.1.1332.1.1.5.3.113.2.1.3;
        }

        leaf msanTacacsServerPrimaryMode {
          type enumeration {
            enum enable {
              value 1;
            }
            enum disable {
              value 2;
            }
          }
          description
           "Configure the TACACS server to be the primary server. If there is any
            other server that is configured to be primary, that server is set to be
            a seconday server and this entry is set Primary.";
          smiv2:max-access read-write;
          smiv2:oid 1.3.6.1.4.1.1332.1.1.5.3.113.2.1.4;
        }

        leaf msanTacacsServerCurrentMode {
          type enumeration {
            enum yes {
              value 1;
            }
            enum no {
              value 2;
            }
          }
          description
           "Indicates if the TACACS server is the current server in user for
            authentication.";
          smiv2:max-access read-only;
          smiv2:oid 1.3.6.1.4.1.1332.1.1.5.3.113.2.1.5;
        }

        leaf msanTacacsServerStatus {
          type snmpv2-tc:RowStatus;
          description
           "Creates or destroys a TACACS server entry.
            
            active(1)       - This entry is active.
            createAndGo(4)  - Creates a new entry.
            destroy(6)      - Deletes an entry.";
          smiv2:max-access read-write;
          smiv2:oid 1.3.6.1.4.1.1332.1.1.5.3.113.2.1.6;
        }
      }
    }
        container msanQosPortTable {
            list msanQosPortEntry {
                key "msanQosPortIfName msanQosPortDirection";
                leaf msanQosPortIfName {

          type if:interface-ref;
                    description "ONU interface name.";
                }
                leaf msanQosPortDirection {

          type enumeration {
            enum downstream {
              value 1;
            }
            enum upstream {
              value 2;
            }
          }
                    description 
                        "Data traffic direction which defines QoS action:
                         downstream(1) -> shaping
                         upstream(2) -> policing
                         ";
                }
                leaf msanQosPortPeakDataRate {

          type uint32 {
            range "0..1000000";
          }
                    units kbps;
                    description 
                        "Peak data rate in kbps (0 | 64  - 1000000).
                         Value 0 (default)  means -> no rate limit";
                }
                leaf msanQosPortPeakBurstSize {

          type uint32 {
            range "0..16384";
          }
                    units kB;
                    description 
                        "Peak data rate burst size in kB (0 - 16384).
                         This parameter can be set only when peak data rate value (msanQosPortPeakDataRate) is not 0.
                         
                         When parameter is set to 0 (default), it's automatically updated to default
                         burst size value according to current peak data rate (msanQosPortPeakDataRate).";
                }
            }
        }

    container msanOltPortSumStatTable {
            config false;

      description
       "Description.";
      smiv2:oid 1.3.6.1.4.1.1332.1.1.5.3.112.3;

      list msanOltPortSumStatEntry {
        key msanOltPortSumStatIfName;
        description
         "Description.";
        smiv2:oid 1.3.6.1.4.1.1332.1.1.5.3.112.3.1;

        leaf msanOltPortSumStatIfName {
          type if:interface-state-ref;
          description
           "Name of OLT interface.";
          smiv2:max-access not-accessible;
          smiv2:oid 1.3.6.1.4.1.1332.1.1.5.3.112.3.1.1;
        }

        leaf msanOltPortSumStatInOmciPkts {
          type yang:counter64;
          units Packets;
          description
           "Received OMCI packets.";
          smiv2:max-access read-only;
          smiv2:oid 1.3.6.1.4.1.1332.1.1.5.3.112.3.1.3;
        }

        leaf msanOltPortSumStatInCpuPkts {
          type yang:counter64;
          units Packets;
          description
           "Received CPU packets.";
          smiv2:max-access read-only;
          smiv2:oid 1.3.6.1.4.1.1332.1.1.5.3.112.3.1.4;
        }

        leaf msanOltPortSumStatInDiscardedPkts {
          type yang:counter64;
          units Packets;
          description
           "Number of dropped received packets.";
          smiv2:max-access read-only;
          smiv2:oid 1.3.6.1.4.1.1332.1.1.5.3.112.3.1.5;
        }

        leaf msanOltPortSumStatInUndersizePkts {
          type yang:counter64;
          units Packets;
          description
           "Received packets dropped due to length too short.";
          smiv2:max-access read-only;
          smiv2:oid 1.3.6.1.4.1.1332.1.1.5.3.112.3.1.6;
        }

        leaf msanOltPortSumStatInOversizePkts {
          type yang:counter64;
          units Packets;
          description
           "Received packets dropped due to length too long.";
          smiv2:max-access read-only;
          smiv2:oid 1.3.6.1.4.1.1332.1.1.5.3.112.3.1.7;
        }

        leaf msanOltPortSumStatInCrcErrorPkts {
          type yang:counter64;
          units Packets;
          description
           "Received packets dropped due to CRC error.";
          smiv2:max-access read-only;
          smiv2:oid 1.3.6.1.4.1.1332.1.1.5.3.112.3.1.8;
        }

        leaf msanOltPortSumStatInKeyErrorPkts {
          type yang:counter64;
          units Packets;
          description
           "Received packets dropped due to Key error.";
          smiv2:max-access read-only;
          smiv2:oid 1.3.6.1.4.1.1332.1.1.5.3.112.3.1.9;
        }

        leaf msanOltPortSumStatInTpidErrorPkts {
          type yang:counter64;
          units Packets;
          description
           "Received packet dropped due to TPID error.";
          smiv2:max-access read-only;
          smiv2:oid 1.3.6.1.4.1.1332.1.1.5.3.112.3.1.10;
        }

        leaf msanOltPortSumStatInVidErrorPkts {
          type yang:counter64;
          units Packets;
          description
           "Received packet dropped due to VID error.";
          smiv2:max-access read-only;
          smiv2:oid 1.3.6.1.4.1.1332.1.1.5.3.112.3.1.11;
        }

        leaf msanOltPortSumStatInFragmentErrorPkts {
          type yang:counter64;
          units Packets;
          description
           "Received packet dropped due to fragmentation error.";
          smiv2:max-access read-only;
          smiv2:oid 1.3.6.1.4.1.1332.1.1.5.3.112.3.1.12;
        }

        leaf msanOltPortSumStatInGemFrames {
          type yang:counter64;
          units Frames;
          description
           "Received GEM frames.";
          smiv2:max-access read-only;
          smiv2:oid 1.3.6.1.4.1.1332.1.1.5.3.112.3.1.13;
        }

        leaf msanOltPortSumStatInDiscardedGemFrames {
          type yang:counter64;
          units Frames;
          description
           "Number of corrected received GEM frames.";
          smiv2:max-access read-only;
          smiv2:oid 1.3.6.1.4.1.1332.1.1.5.3.112.3.1.14;
        }

        leaf msanOltPortSumStatInIdleGemFrames {
          type yang:counter64;
          units Frames;
          description
           "Number of idle received GEM frames.";
          smiv2:max-access read-only;
          smiv2:oid 1.3.6.1.4.1.1332.1.1.5.3.112.3.1.15;
        }

        leaf msanOltPortSumStatInCorrectedGemFrames {
          type yang:counter64;
          units Frames;
          description
           "Number of corrected received GEM frames.";
          smiv2:max-access read-only;
          smiv2:oid 1.3.6.1.4.1.1332.1.1.5.3.112.3.1.16;
        }

        leaf msanOltPortSumStatInIllegalGemFrames {
          type yang:counter64;
          units Frames;
          description
           "Number of illegal received GEM frames.";
          smiv2:max-access read-only;
          smiv2:oid 1.3.6.1.4.1.1332.1.1.5.3.112.3.1.17;
        }

        leaf msanOltPortSumStatInValidAllocations {
          type yang:counter64;
          units Allocations;
          description
           "Number of received valid allocations.";
          smiv2:max-access read-only;
          smiv2:oid 1.3.6.1.4.1.1332.1.1.5.3.112.3.1.18;
        }

        leaf msanOltPortSumStatInInvalidAllocations {
          type yang:counter64;
          units Allocations;
          description
           "Number of received invalid allocations.";
          smiv2:max-access read-only;
          smiv2:oid 1.3.6.1.4.1.1332.1.1.5.3.112.3.1.19;
        }

        leaf msanOltPortSumStatInDisabledAllocations {
          type yang:counter64;
          units Allocations;
          description
           "Number of received disabled allocations.";
          smiv2:max-access read-only;
          smiv2:oid 1.3.6.1.4.1.1332.1.1.5.3.112.3.1.20;
        }

        leaf msanOltPortSumStatInPloamMsgs {
          type yang:counter64;
          units "PLOAM messages";
          description
           "Number of received PLOAM (physical layer operations and maintenance) messages.";
          smiv2:max-access read-only;
          smiv2:oid 1.3.6.1.4.1.1332.1.1.5.3.112.3.1.21;
        }

        leaf msanOltPortSumStatInNonIdlePloamMsgs {
          type yang:counter64;
          units Messages;
          description
           "Number of received non-idle PLOAM (physical layer operations and maintenance) messages.";
          smiv2:max-access read-only;
          smiv2:oid 1.3.6.1.4.1.1332.1.1.5.3.112.3.1.22;
        }

        leaf msanOltPortSumStatInErrorPloamMsgs {
          type yang:counter64;
          units Messages;
          description
           "Number of received PLOAM (physical layer operations and maintenance) messages with errors.";
          smiv2:max-access read-only;
          smiv2:oid 1.3.6.1.4.1.1332.1.1.5.3.112.3.1.23;
        }

        leaf msanOltPortSumStatInDiscardedPloamMsgs {
          type yang:counter64;
          units Messages;
          description
           "Number of discarded PLOAM (physical layer operations and maintenance) messages.";
          smiv2:max-access read-only;
          smiv2:oid 1.3.6.1.4.1.1332.1.1.5.3.112.3.1.24;
        }

        leaf msanOltPortSumStatInFecCodewords {
          type yang:counter64;
          description
           "Number of received FEC (Forward error correction) codewords.";
          smiv2:max-access read-only;
          smiv2:oid 1.3.6.1.4.1.1332.1.1.5.3.112.3.1.25;
        }

        leaf msanOltPortSumStatInUncorrectedFecCodewords {
          type yang:counter64;
          description
           "Number of received uncorrected FEC (Forward error correction) codewords.";
          smiv2:max-access read-only;
          smiv2:oid 1.3.6.1.4.1.1332.1.1.5.3.112.3.1.26;
        }

        leaf msanOltPortSumStatInBip8ProtectedBytes {
          type yang:counter64;
          units Bytes;
          description
           "Number of received bytes protected by Bip8.";
          smiv2:max-access read-only;
          smiv2:oid 1.3.6.1.4.1.1332.1.1.5.3.112.3.1.27;
        }

        leaf msanOltPortSumStatInBip8ErrorBytes {
          type yang:counter64;
          units Bytes;
          description
           "Number of received bytes with Bip8 error.";
          smiv2:max-access read-only;
          smiv2:oid 1.3.6.1.4.1.1332.1.1.5.3.112.3.1.28;
        }

        leaf msanOltPortSumStatOutOmciPkts {
          type yang:counter64;
          units Packets;
          description
           "Transmitted OMCI packets.";
          smiv2:max-access read-only;
          smiv2:oid 1.3.6.1.4.1.1332.1.1.5.3.112.3.1.29;
        }

        leaf msanOltPortSumStatOutCpuPkts {
          type yang:counter64;
          units Packets;
          description
           "Transmitted CPU packets.";
          smiv2:max-access read-only;
          smiv2:oid 1.3.6.1.4.1.1332.1.1.5.3.112.3.1.30;
        }

        leaf msanOltPortSumStatOutDiscardedPkts {
          type yang:counter64;
          units Packets;
          description
           "Number of dropped transmitted packets because of illegal length.";
          smiv2:max-access read-only;
          smiv2:oid 1.3.6.1.4.1.1332.1.1.5.3.112.3.1.31;
        }

        leaf msanOltPortSumStatOutGemFrames {
          type yang:counter64;
          units Frames;
          description
           "Transmitted GEM frames.";
          smiv2:max-access read-only;
          smiv2:oid 1.3.6.1.4.1.1332.1.1.5.3.112.3.1.32;
        }

        leaf msanOltPortSumStatOutPloamMsgs {
          type yang:counter64;
          units "PLOAM messages";
          description
           "Number of transmitted PLOAM (physical layer operations and maintenance) messages.";
          smiv2:max-access read-only;
          smiv2:oid 1.3.6.1.4.1.1332.1.1.5.3.112.3.1.33;
        }
      }
    }

  }

  smiv2:alias msanXdsl2LineConfTemplateTable {
    description
     "Description.";
    smiv2:oid 1.3.6.1.4.1.1332.1.1.5.3.3.8.1;
  }

  smiv2:alias msanXdsl2LineConfTemplateEntry {
    description
     "Description.";
    smiv2:oid 1.3.6.1.4.1.1332.1.1.5.3.3.8.1.1;
  }

  augment "/vdsl2-line:VDSL2-LINE-MIB/vdsl2-line:xdsl2LineConfTemplateTable/vdsl2-line:xdsl2LineConfTemplateEntry" {
    description
     "Description.";
    smiv2:oid 1.3.6.1.4.1.1332.1.1.5.3.3.8.1.1;

    leaf msanXdsl2LineConfTempProtection {
      type enumeration {
        enum unprotected {
          value 0;
        }
        enum protected {
          value 1;
        }
      }
      description
       "If protection flag is set to protected (1), other profile values cannot be edited.
        
        Protection flag is always  protected (1) and it can't be changed if  profile is assigned as dynamic:
        msanAclProfileStatus = dynamic(2)";
      smiv2:defval unprotected;
      smiv2:max-access read-write;
      smiv2:oid 1.3.6.1.4.1.1332.1.1.5.3.3.8.1.1.1;
    }

    leaf msanXdsl2LineConfTempStatus {
      type enumeration {
        enum static {
          value 1;
        }
        enum dynamic {
          value 2;
        }
      }
      description
       "Profile status.
        If status is dynamic, profile values can't be edited.";
      smiv2:max-access read-only;
      smiv2:oid 1.3.6.1.4.1.1332.1.1.5.3.3.8.1.1.2;
    }
  }

  smiv2:alias msanXdsl2LineAlarmConfTemplateTable {
    description
     "Description.";
    smiv2:oid 1.3.6.1.4.1.1332.1.1.5.3.3.8.2;
  }

  smiv2:alias msanXdsl2LineAlarmConfTemplateEntry {
    description
     "Description.";
    smiv2:oid 1.3.6.1.4.1.1332.1.1.5.3.3.8.2.1;
  }

  augment "/vdsl2-line:VDSL2-LINE-MIB/vdsl2-line:xdsl2LineAlarmConfTemplateTable/vdsl2-line:xdsl2LineAlarmConfTemplateEntry" {
    description
     "Description.";
    smiv2:oid 1.3.6.1.4.1.1332.1.1.5.3.3.8.2.1;

    leaf msanXdsl2LineAlarmConfTempProtection {
      type enumeration {
        enum unprotected {
          value 0;
        }
        enum protected {
          value 1;
        }
      }
      description
       "If protection flag is set to protected (1), other profile values cannot be edited.
        
        Protection flag is always  protected (1) and it can't be changed if  profile is assigned as dynamic:
        msanAclProfileStatus = dynamic(2)";
      smiv2:defval unprotected;
      smiv2:max-access read-write;
      smiv2:oid 1.3.6.1.4.1.1332.1.1.5.3.3.8.2.1.1;
    }

    leaf msanXdsl2LineAlarmConfTempStatus {
      type enumeration {
        enum static {
          value 1;
        }
        enum dynamic {
          value 2;
        }
      }
      description
       "Profile status.
        If status is dynamic, profile values can't be edited.";
      smiv2:max-access read-only;
      smiv2:oid 1.3.6.1.4.1.1332.1.1.5.3.3.8.2.1.2;
    }
  }

  notification msanSnmpOnuIfStatusChanged {
    description
     "ONU interface status changed notification.";
    smiv2:oid 1.3.6.1.4.1.1332.1.1.5.3.7.2.1;

    container object-1 {

      leaf ifIndex {
        type leafref {
          path "/if-mib:interfaces/if-mib:ifEntry/if-mib:ifIndex";
        }
      }

      leaf ifDescr {
        type leafref {
          path "/if-mib:interfaces/if-mib:ifEntry/if-mib:ifDescr";
        }
      }
    }

    container object-2 {

      leaf ifIndex {
        type leafref {
          path "/if-mib:interfaces/if-mib:ifEntry/if-mib:ifIndex";
        }
      }

      leaf ifAdminStatus {
        type leafref {
          path "/if-mib:interfaces/if-mib:ifEntry/if-mib:ifAdminStatus";
        }
      }
    }

    container object-3 {

      leaf ifIndex {
        type leafref {
          path "/if-mib:interfaces/if-mib:ifEntry/if-mib:ifIndex";
        }
      }

      leaf ifOperStatus {
        type leafref {
          path "/if-mib:interfaces/if-mib:ifEntry/if-mib:ifOperStatus";
        }
      }
    }

    container object-4 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoSerialNumber {
        type leafref {
          path "/iskratel-msan:ISKRATEL-MSAN-MIB/iskratel-msan:msanOnuInfoTable/iskratel-msan:msanOnuInfoEntry/iskratel-msan:msanOnuInfoSerialNumber";
        }
      }
    }

    container object-5 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoVersion {
        type leafref {
          path "/iskratel-msan:ISKRATEL-MSAN-MIB/iskratel-msan:msanOnuInfoTable/iskratel-msan:msanOnuInfoEntry/iskratel-msan:msanOnuInfoVersion";
        }
      }
    }

    container object-6 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoEquipmentId {
        type leafref {
          path "/iskratel-msan:ISKRATEL-MSAN-MIB/iskratel-msan:msanOnuInfoTable/iskratel-msan:msanOnuInfoEntry/iskratel-msan:msanOnuInfoEquipmentId";
        }
      }
    }

    container object-7 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuHardwareType {
        type leafref {
          path "/iskratel-msan:ISKRATEL-MSAN-MIB/iskratel-msan:msanOnuInfoTable/iskratel-msan:msanOnuInfoEntry/iskratel-msan:msanOnuInfoOnuHardwareType";
        }
      }
    }

    container object-8 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance0Version {
        type leafref {
          path "/iskratel-msan:ISKRATEL-MSAN-MIB/iskratel-msan:msanOnuInfoTable/iskratel-msan:msanOnuInfoEntry/iskratel-msan:msanOnuInfoOnuImageInstance0Version";
        }
      }
    }

    container object-9 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance0Valid {
        type leafref {
          path "/iskratel-msan:ISKRATEL-MSAN-MIB/iskratel-msan:msanOnuInfoTable/iskratel-msan:msanOnuInfoEntry/iskratel-msan:msanOnuInfoOnuImageInstance0Valid";
        }
      }
    }

    container object-10 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance0Activate {
        type leafref {
          path "/iskratel-msan:ISKRATEL-MSAN-MIB/iskratel-msan:msanOnuInfoTable/iskratel-msan:msanOnuInfoEntry/iskratel-msan:msanOnuInfoOnuImageInstance0Activate";
        }
      }
    }

    container object-11 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance1Version {
        type leafref {
          path "/iskratel-msan:ISKRATEL-MSAN-MIB/iskratel-msan:msanOnuInfoTable/iskratel-msan:msanOnuInfoEntry/iskratel-msan:msanOnuInfoOnuImageInstance1Version";
        }
      }
    }

    container object-12 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance1Valid {
        type leafref {
          path "/iskratel-msan:ISKRATEL-MSAN-MIB/iskratel-msan:msanOnuInfoTable/iskratel-msan:msanOnuInfoEntry/iskratel-msan:msanOnuInfoOnuImageInstance1Valid";
        }
      }
    }

    container object-13 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuImageInstance1Activate {
        type leafref {
          path "/iskratel-msan:ISKRATEL-MSAN-MIB/iskratel-msan:msanOnuInfoTable/iskratel-msan:msanOnuInfoEntry/iskratel-msan:msanOnuInfoOnuImageInstance1Activate";
        }
      }
    }

    container object-14 {

      leaf msanOnuInfoIfName {
        type leafref {
          path "/iskratel-msan:ISKRATEL-MSAN-MIB/iskratel-msan:msanOnuInfoTable/iskratel-msan:msanOnuInfoEntry/iskratel-msan:msanOnuInfoIfName";
        }
      }

      leaf msanOnuInfoOnuMacAddress {
        type leafref {
          path "/iskratel-msan:ISKRATEL-MSAN-MIB/iskratel-msan:msanOnuInfoTable/iskratel-msan:msanOnuInfoEntry/iskratel-msan:msanOnuInfoOnuMacAddress";
        }
      }
    }

    container object-15 {

      leaf msanOnuIfOperStatusChangeCnt {
        type leafref {
          path "/iskratel-msan:ISKRATEL-MSAN-MIB/iskratel-msan:msanOnuGlobal/iskratel-msan:msanOnuIfOperStatusChangeCnt";
        }
      }
    }
  }

  notification msanSnmpOnuBlackListAdded {
    description
     "ONU added to Blacklist notification.";
    smiv2:oid 1.3.6.1.4.1.1332.1.1.5.3.7.2.2;

    container object-1 {

      leaf ifIndex {
        type leafref {
          path "/if-mib:interfaces/if-mib:ifEntry/if-mib:ifIndex";
        }
      }

      leaf ifDescr {
        type leafref {
          path "/if-mib:interfaces/if-mib:ifEntry/if-mib:ifDescr";
        }
      }
    }

    container object-2 {

      leaf msanOnuBlackListIfName {
        type leafref {
          path "/iskratel-msan:ISKRATEL-MSAN-MIB/iskratel-msan:msanOnuBlackListTable/iskratel-msan:msanOnuBlackListEntry/iskratel-msan:msanOnuBlackListIfName";
        }
      }

      leaf msanOnuBlackListSerialNumber {
        type rfc1213-mib:DisplayString {
          length "16";
        }
        description
         "The serial number. Index for this table.
          The serial number is unique for each ONT.
          
          It is defined in ITU-T G.984.3 and contains
          the vendor id and version number. The first
          four bytes are an ASCII encoded vendor ID
          four letter mnemonic. The second four bytes
          are a binary encoded serial number, under the
          control of the ONT vendor. (R) (mandatory) (8 bytes).";
        smiv2:max-access not-accessible;
        smiv2:oid 1.3.6.1.4.1.1332.1.1.5.3.111.8.1.2;
      }
    }

    container object-3 {

      leaf msanOnuBlackListIfName {
        type leafref {
          path "/iskratel-msan:ISKRATEL-MSAN-MIB/iskratel-msan:msanOnuBlackListTable/iskratel-msan:msanOnuBlackListEntry/iskratel-msan:msanOnuBlackListIfName";
        }
      }

      leaf msanOnuBlackListSerialNumber {
        type leafref {
          path "/iskratel-msan:ISKRATEL-MSAN-MIB/iskratel-msan:msanOnuBlackListTable/iskratel-msan:msanOnuBlackListEntry/iskratel-msan:msanOnuBlackListSerialNumber";
        }
      }

      leaf msanOnuBlackListPassword {
        type leafref {
          path "/iskratel-msan:ISKRATEL-MSAN-MIB/iskratel-msan:msanOnuBlackListTable/iskratel-msan:msanOnuBlackListEntry/iskratel-msan:msanOnuBlackListPassword";
        }
      }
    }

    container object-4 {

      leaf msanOnuBlackListIfName {
        type leafref {
          path "/iskratel-msan:ISKRATEL-MSAN-MIB/iskratel-msan:msanOnuBlackListTable/iskratel-msan:msanOnuBlackListEntry/iskratel-msan:msanOnuBlackListIfName";
        }
      }

      leaf msanOnuBlackListSerialNumber {
        type leafref {
          path "/iskratel-msan:ISKRATEL-MSAN-MIB/iskratel-msan:msanOnuBlackListTable/iskratel-msan:msanOnuBlackListEntry/iskratel-msan:msanOnuBlackListSerialNumber";
        }
      }

      leaf msanOnuBlackListCause {
        type leafref {
          path "/iskratel-msan:ISKRATEL-MSAN-MIB/iskratel-msan:msanOnuBlackListTable/iskratel-msan:msanOnuBlackListEntry/iskratel-msan:msanOnuBlackListCause";
        }
      }
    }

    container object-5 {

      leaf msanOnuBlackListChangeCnt {
        type leafref {
          path "/iskratel-msan:ISKRATEL-MSAN-MIB/iskratel-msan:msanOnuGlobal/iskratel-msan:msanOnuBlackListChangeCnt";
        }
      }
    }
  }

  notification msanSnmpOnuBlackListRemoved {
    description
     "ONU removed from Blacklist notification.";
    smiv2:oid 1.3.6.1.4.1.1332.1.1.5.3.7.2.3;

    container object-1 {

      leaf ifIndex {
        type leafref {
          path "/if-mib:interfaces/if-mib:ifEntry/if-mib:ifIndex";
        }
      }

      leaf ifDescr {
        type leafref {
          path "/if-mib:interfaces/if-mib:ifEntry/if-mib:ifDescr";
        }
      }
    }

    container object-2 {

      leaf msanOnuBlackListIfName {
        type leafref {
          path "/iskratel-msan:ISKRATEL-MSAN-MIB/iskratel-msan:msanOnuBlackListTable/iskratel-msan:msanOnuBlackListEntry/iskratel-msan:msanOnuBlackListIfName";
        }
      }

      leaf msanOnuBlackListSerialNumber {
        type rfc1213-mib:DisplayString {
          length "16";
        }
        description
         "The serial number. Index for this table.
          The serial number is unique for each ONT.
          
          It is defined in ITU-T G.984.3 and contains
          the vendor id and version number. The first
          four bytes are an ASCII encoded vendor ID
          four letter mnemonic. The second four bytes
          are a binary encoded serial number, under the
          control of the ONT vendor. (R) (mandatory) (8 bytes).";
        smiv2:max-access not-accessible;
        smiv2:oid 1.3.6.1.4.1.1332.1.1.5.3.111.8.1.2;
      }
    }

    container object-3 {

      leaf msanOnuBlackListChangeCnt {
        type leafref {
          path "/iskratel-msan:ISKRATEL-MSAN-MIB/iskratel-msan:msanOnuGlobal/iskratel-msan:msanOnuBlackListChangeCnt";
        }
      }
    }
  }

  notification msanSnmpIfStatusChanged {
    description
     "Interface status changed notification.";
    smiv2:oid 1.3.6.1.4.1.1332.1.1.5.3.7.2.4;

    container object-1 {

      leaf ifIndex {
        type leafref {
          path "/if-mib:interfaces/if-mib:ifEntry/if-mib:ifIndex";
        }
      }

      leaf ifDescr {
        type leafref {
          path "/if-mib:interfaces/if-mib:ifEntry/if-mib:ifDescr";
        }
      }
    }

    container object-2 {

      leaf ifIndex {
        type leafref {
          path "/if-mib:interfaces/if-mib:ifEntry/if-mib:ifIndex";
        }
      }

      leaf ifAdminStatus {
        type leafref {
          path "/if-mib:interfaces/if-mib:ifEntry/if-mib:ifAdminStatus";
        }
      }
    }

    container object-3 {

      leaf ifIndex {
        type leafref {
          path "/if-mib:interfaces/if-mib:ifEntry/if-mib:ifIndex";
        }
      }

      leaf ifOperStatus {
        type leafref {
          path "/if-mib:interfaces/if-mib:ifEntry/if-mib:ifOperStatus";
        }
      }
    }

    container object-4 {

      leaf msanIfOperStatusChangeCnt {
        type leafref {
          path "/iskratel-msan:ISKRATEL-MSAN-MIB/iskratel-msan:msanSnmpGlobal/iskratel-msan:msanIfOperStatusChangeCnt";
        }
      }
    }
  }

  smiv2:alias org {
    smiv2:oid 1.3;
  }

  smiv2:alias dod {
    smiv2:oid 1.3.6;
  }

  smiv2:alias internet {
    smiv2:oid 1.3.6.1;
  }

  smiv2:alias directory {
    smiv2:oid 1.3.6.1.1;
  }

  smiv2:alias mgmt {
    smiv2:oid 1.3.6.1.2;
  }

  smiv2:alias mib-2 {
    smiv2:oid 1.3.6.1.2.1;
  }

  smiv2:alias transmission {
    smiv2:oid 1.3.6.1.2.1.10;
  }

  smiv2:alias experimental {
    smiv2:oid 1.3.6.1.3;
  }

  smiv2:alias private {
    smiv2:oid 1.3.6.1.4;
  }

  smiv2:alias enterprises {
    smiv2:oid 1.3.6.1.4.1;
  }

  smiv2:alias iskratel {
    smiv2:oid 1.3.6.1.4.1.1332;
  }

  smiv2:alias si2000 {
    smiv2:oid 1.3.6.1.4.1.1332.1;
  }

  smiv2:alias products {
    smiv2:oid 1.3.6.1.4.1.1332.1.1;
  }

  smiv2:alias msan {
    smiv2:oid 1.3.6.1.4.1.1332.1.1.5;
  }

  smiv2:alias msanInfo {
    smiv2:oid 1.3.6.1.4.1.1332.1.1.5.1;
  }

  smiv2:alias msanShelfInfo {
    smiv2:oid 1.3.6.1.4.1.1332.1.1.5.1.1;
  }

  smiv2:alias msanBoardInfo {
    smiv2:oid 1.3.6.1.4.1.1332.1.1.5.1.2;
  }

  smiv2:alias msanSwInfo {
    smiv2:oid 1.3.6.1.4.1.1332.1.1.5.1.3;
  }

  smiv2:alias msanOtherInfo {
    smiv2:oid 1.3.6.1.4.1.1332.1.1.5.1.4;
  }

  smiv2:alias msanLicense {
    smiv2:oid 1.3.6.1.4.1.1332.1.1.5.1.5;
  }

  smiv2:alias msanLicenseGlobal {
    smiv2:oid 1.3.6.1.4.1.1332.1.1.5.1.5.1;
  }

  smiv2:alias msanResources {
    smiv2:oid 1.3.6.1.4.1.1332.1.1.5.1.6;
  }

  smiv2:alias msanCpu {
    smiv2:oid 1.3.6.1.4.1.1332.1.1.5.1.6.1;
  }

  smiv2:alias msanDisk {
    smiv2:oid 1.3.6.1.4.1.1332.1.1.5.1.6.2;
  }

  smiv2:alias msanMemory {
    smiv2:oid 1.3.6.1.4.1.1332.1.1.5.1.6.3;
  }

  smiv2:alias msanAdditionalConf {
    smiv2:oid 1.3.6.1.4.1.1332.1.1.5.3;
  }

  smiv2:alias msanSystem {
    smiv2:oid 1.3.6.1.4.1.1332.1.1.5.3.1;
  }

  smiv2:alias msanSystemSwUpgrade {
    smiv2:oid 1.3.6.1.4.1.1332.1.1.5.3.1.10;
  }

  smiv2:alias msanSystemLogsUpload {
    smiv2:oid 1.3.6.1.4.1.1332.1.1.5.3.1.11;
  }

  smiv2:alias msanSystemAutoSaveConfig {
    smiv2:oid 1.3.6.1.4.1.1332.1.1.5.3.1.12;
  }

  smiv2:alias msanProfiles {
    smiv2:oid 1.3.6.1.4.1.1332.1.1.5.3.3;
  }

  smiv2:alias msanServiceProfile {
    smiv2:oid 1.3.6.1.4.1.1332.1.1.5.3.3.2;
  }

  smiv2:alias msanServiceFlowProfile {
    smiv2:oid 1.3.6.1.4.1.1332.1.1.5.3.3.3;
  }

  smiv2:alias msanVlanProfile {
    smiv2:oid 1.3.6.1.4.1.1332.1.1.5.3.3.4;
  }

  smiv2:alias msanMulticastProfile {
    smiv2:oid 1.3.6.1.4.1.1332.1.1.5.3.3.5;
  }

  smiv2:alias msanSecurityProfile {
    smiv2:oid 1.3.6.1.4.1.1332.1.1.5.3.3.6;
  }

  smiv2:alias msanL2cpProfile {
    smiv2:oid 1.3.6.1.4.1.1332.1.1.5.3.3.7;
  }

  smiv2:alias msanXdslProfile {
    smiv2:oid 1.3.6.1.4.1.1332.1.1.5.3.3.8;
  }

  smiv2:alias msanOnuFlowProfile {
    smiv2:oid 1.3.6.1.4.1.1332.1.1.5.3.3.20;
  }

  smiv2:alias msanOnuVlanProfile {
    smiv2:oid 1.3.6.1.4.1.1332.1.1.5.3.3.21;
  }

  smiv2:alias msanOnuMulticastProfile {
    smiv2:oid 1.3.6.1.4.1.1332.1.1.5.3.3.22;
  }

  smiv2:alias msanOnuTcontProfile {
    smiv2:oid 1.3.6.1.4.1.1332.1.1.5.3.3.23;
  }

  smiv2:alias msanDhcpRelay {
    smiv2:oid 1.3.6.1.4.1.1332.1.1.5.3.4;
  }

  smiv2:alias msanDhcpRaGlobal {
    smiv2:oid 1.3.6.1.4.1.1332.1.1.5.3.4.1;
  }

  smiv2:alias msanDhcpRaStatGlobal {
    smiv2:oid 1.3.6.1.4.1.1332.1.1.5.3.4.4;
  }

  smiv2:alias msanDhcpv6RaGlobal {
    smiv2:oid 1.3.6.1.4.1.1332.1.1.5.3.4.100;
  }

  smiv2:alias msanDhcpv6RaStatistics {
    smiv2:oid 1.3.6.1.4.1.1332.1.1.5.3.4.101;
  }

  smiv2:alias msanSntp {
    smiv2:oid 1.3.6.1.4.1.1332.1.1.5.3.5;
  }

  smiv2:alias msanSntpGlobal {
    smiv2:oid 1.3.6.1.4.1.1332.1.1.5.3.5.1;
  }

  smiv2:alias msanSnmp {
    smiv2:oid 1.3.6.1.4.1.1332.1.1.5.3.7;
  }

  smiv2:alias msanSnmpGlobal {
    smiv2:oid 1.3.6.1.4.1.1332.1.1.5.3.7.1;
  }

  smiv2:alias msanSnmpNotifications {
    smiv2:oid 1.3.6.1.4.1.1332.1.1.5.3.7.2;
  }

  smiv2:alias msanIgmpSnooping {
    smiv2:oid 1.3.6.1.4.1.1332.1.1.5.3.8;
  }

  smiv2:alias msanIgmpSnoopingGlobal {
    smiv2:oid 1.3.6.1.4.1.1332.1.1.5.3.8.1;
  }

  smiv2:alias msanIgmpStatistics {
    smiv2:oid 1.3.6.1.4.1.1332.1.1.5.3.8.8;
  }

  smiv2:alias msanIgmpStatGlobal {
    smiv2:oid 1.3.6.1.4.1.1332.1.1.5.3.8.8.1;
  }

  smiv2:alias msanPort {
    smiv2:oid 1.3.6.1.4.1.1332.1.1.5.3.10;
  }

  smiv2:alias msanPortGlobal {
    smiv2:oid 1.3.6.1.4.1.1332.1.1.5.3.10.1;
  }

  smiv2:alias msanPppoeIA {
    smiv2:oid 1.3.6.1.4.1.1332.1.1.5.3.11;
  }

  smiv2:alias msanPppoeIAGlobal {
    smiv2:oid 1.3.6.1.4.1.1332.1.1.5.3.11.1;
  }

  smiv2:alias msanPppoeIaStatistics {
    smiv2:oid 1.3.6.1.4.1.1332.1.1.5.3.11.3;
  }

  smiv2:alias msanQoS {
    smiv2:oid 1.3.6.1.4.1.1332.1.1.5.3.12;
  }

  smiv2:alias msanQosGlobal {
    smiv2:oid 1.3.6.1.4.1.1332.1.1.5.3.12.1;
  }

  smiv2:alias msanQosStatistics {
    smiv2:oid 1.3.6.1.4.1.1332.1.1.5.3.12.9;
  }

  smiv2:alias msanForwardingDb {
    smiv2:oid 1.3.6.1.4.1.1332.1.1.5.3.13;
  }

  smiv2:alias msanForwardingDbGlobal {
    smiv2:oid 1.3.6.1.4.1.1332.1.1.5.3.13.3;
  }

  smiv2:alias msanDiagnostics {
    smiv2:oid 1.3.6.1.4.1.1332.1.1.5.3.14;
  }

  smiv2:alias msanDiagnosticsGlobal {
    smiv2:oid 1.3.6.1.4.1.1332.1.1.5.3.14.1;
  }

  smiv2:alias msanPpp {
    smiv2:oid 1.3.6.1.4.1.1332.1.1.5.3.15;
  }

  smiv2:alias msanPppGlobal {
    smiv2:oid 1.3.6.1.4.1.1332.1.1.5.3.15.1;
  }

  smiv2:alias msanAlarmPanel ;

  smiv2:alias msanRemoteAccess {
    smiv2:oid 1.3.6.1.4.1.1332.1.1.5.3.18;
  }

  smiv2:alias msanRemoteAccessGlobal {
    smiv2:oid 1.3.6.1.4.1.1332.1.1.5.3.18.1;
  }

  smiv2:alias msanDslSpecific {
    smiv2:oid 1.3.6.1.4.1.1332.1.1.5.3.19;
  }

  smiv2:alias msanDslSpecificGlobal {
    smiv2:oid 1.3.6.1.4.1.1332.1.1.5.3.19.1;
  }

  smiv2:alias msanPortMirroring {
    smiv2:oid 1.3.6.1.4.1.1332.1.1.5.3.20;
  }

  smiv2:alias msanPortMirroringGlobal {
    smiv2:oid 1.3.6.1.4.1.1332.1.1.5.3.20.1;
  }

  smiv2:alias msanResetWithDelay {
    smiv2:oid 1.3.6.1.4.1.1332.1.1.5.3.21;
  }

  smiv2:alias msanResetWithDelayGlobal {
    smiv2:oid 1.3.6.1.4.1.1332.1.1.5.3.21.1;
  }

  smiv2:alias msanMacTable {
    smiv2:oid 1.3.6.1.4.1.1332.1.1.5.3.22;
  }

  smiv2:alias msanMacTableGlobal {
    smiv2:oid 1.3.6.1.4.1.1332.1.1.5.3.22.1;
  }

  smiv2:alias msanAcs {
    smiv2:oid 1.3.6.1.4.1.1332.1.1.5.3.23;
  }

  smiv2:alias msanAcsGlobal {
    smiv2:oid 1.3.6.1.4.1.1332.1.1.5.3.23.1;
  }

  smiv2:alias msanStp {
    smiv2:oid 1.3.6.1.4.1.1332.1.1.5.3.24;
  }

  smiv2:alias msanStpGlobal {
    smiv2:oid 1.3.6.1.4.1.1332.1.1.5.3.24.1;
  }

  smiv2:alias msanStpSwitchConfigGroup {
    smiv2:oid 1.3.6.1.4.1.1332.1.1.5.3.24.3;
  }

  smiv2:alias msanAuthentication {
    smiv2:oid 1.3.6.1.4.1.1332.1.1.5.3.25;
  }

  smiv2:alias msanAuthenticationGlobal {
    smiv2:oid 1.3.6.1.4.1.1332.1.1.5.3.25.1;
  }

  smiv2:alias msanPortSecurity {
    smiv2:oid 1.3.6.1.4.1.1332.1.1.5.3.26;
  }

  smiv2:alias msanPortSecurityGlobal {
    smiv2:oid 1.3.6.1.4.1.1332.1.1.5.3.26.1;
  }

  smiv2:alias msanLag {
    smiv2:oid 1.3.6.1.4.1.1332.1.1.5.3.27;
  }

  smiv2:alias msanLagGlobal {
    smiv2:oid 1.3.6.1.4.1.1332.1.1.5.3.27.1;
  }

  smiv2:alias msanRadiusServer {
    smiv2:oid 1.3.6.1.4.1.1332.1.1.5.3.28;
  }

  smiv2:alias msanRadiusServerGlobal {
    smiv2:oid 1.3.6.1.4.1.1332.1.1.5.3.28.1;
  }

  smiv2:alias msanNetwork {
    smiv2:oid 1.3.6.1.4.1.1332.1.1.5.3.29;
  }

  smiv2:alias msanNetworkGlobal {
    smiv2:oid 1.3.6.1.4.1.1332.1.1.5.3.29.1;
  }

  smiv2:alias msanStormControl {
    smiv2:oid 1.3.6.1.4.1.1332.1.1.5.3.30;
  }

  smiv2:alias msanStormControlGlobal {
    smiv2:oid 1.3.6.1.4.1.1332.1.1.5.3.30.1;
  }

  smiv2:alias msanUserConfig {
    smiv2:oid 1.3.6.1.4.1.1332.1.1.5.3.31;
  }

  smiv2:alias msanUserConfigGlobal {
    smiv2:oid 1.3.6.1.4.1.1332.1.1.5.3.31.1;
  }

  smiv2:alias msanSfp {
    smiv2:oid 1.3.6.1.4.1.1332.1.1.5.3.32;
  }

  smiv2:alias msanSfpGlobal {
    smiv2:oid 1.3.6.1.4.1.1332.1.1.5.3.32.1;
  }

  smiv2:alias msanMacSg {
    smiv2:oid 1.3.6.1.4.1.1332.1.1.5.3.34;
  }

  smiv2:alias msanMacSgGlobal {
    smiv2:oid 1.3.6.1.4.1.1332.1.1.5.3.34.1;
  }

  smiv2:alias msanErrorDisable {
    smiv2:oid 1.3.6.1.4.1.1332.1.1.5.3.35;
  }

  smiv2:alias msanErrorDisableGlobal {
    smiv2:oid 1.3.6.1.4.1.1332.1.1.5.3.35.1;
  }

  smiv2:alias msanAdsl {
    smiv2:oid 1.3.6.1.4.1.1332.1.1.5.3.36;
  }

  smiv2:alias msanAdslGlobal {
    smiv2:oid 1.3.6.1.4.1.1332.1.1.5.3.36.1;
  }

  smiv2:alias msanEaps {
    smiv2:oid 1.3.6.1.4.1.1332.1.1.5.3.37;
  }

  smiv2:alias msanEapsGlobal {
    smiv2:oid 1.3.6.1.4.1.1332.1.1.5.3.37.1;
  }

  smiv2:alias msanCpe {
    smiv2:oid 1.3.6.1.4.1.1332.1.1.5.3.38;
  }

  smiv2:alias msanCpeGlobal {
    smiv2:oid 1.3.6.1.4.1.1332.1.1.5.3.38.1;
  }

  smiv2:alias msanBoard {
    smiv2:oid 1.3.6.1.4.1.1332.1.1.5.3.39;
  }

  smiv2:alias msanBoardGlobal {
    smiv2:oid 1.3.6.1.4.1.1332.1.1.5.3.39.1;
  }

  smiv2:alias msanFtpServer {
    smiv2:oid 1.3.6.1.4.1.1332.1.1.5.3.40;
  }

  smiv2:alias msanFtpServerGlobal {
    smiv2:oid 1.3.6.1.4.1.1332.1.1.5.3.40.1;
  }

  smiv2:alias msanAppRateLimit {
    smiv2:oid 1.3.6.1.4.1.1332.1.1.5.3.41;
  }

  smiv2:alias msanAppRateLimitGlobal {
    smiv2:oid 1.3.6.1.4.1.1332.1.1.5.3.41.1;
  }

  smiv2:alias msanMlinec {
    smiv2:oid 1.3.6.1.4.1.1332.1.1.5.3.50;
  }

  smiv2:alias msanMlinecGlobal {
    smiv2:oid 1.3.6.1.4.1.1332.1.1.5.3.50.1;
  }

  smiv2:alias msanMulticast {
    smiv2:oid 1.3.6.1.4.1.1332.1.1.5.3.100;
  }

  smiv2:alias msanMulticastGlobal {
    smiv2:oid 1.3.6.1.4.1.1332.1.1.5.3.100.1;
  }

  smiv2:alias msanFiltering {
    smiv2:oid 1.3.6.1.4.1.1332.1.1.5.3.101;
  }

  smiv2:alias msanFilteringGlobal {
    smiv2:oid 1.3.6.1.4.1.1332.1.1.5.3.101.2;
  }

  smiv2:alias msanBridge {
    smiv2:oid 1.3.6.1.4.1.1332.1.1.5.3.102;
  }

  smiv2:alias msanBridgeGlobal {
    smiv2:oid 1.3.6.1.4.1.1332.1.1.5.3.102.1;
  }

  smiv2:alias msanIPSG {
    smiv2:oid 1.3.6.1.4.1.1332.1.1.5.3.103;
  }

  smiv2:alias msanIPSGGlobal {
    smiv2:oid 1.3.6.1.4.1.1332.1.1.5.3.103.1;
  }

  smiv2:alias msanVlan {
    smiv2:oid 1.3.6.1.4.1.1332.1.1.5.3.105;
  }

  smiv2:alias msanVlanGlobal {
    smiv2:oid 1.3.6.1.4.1.1332.1.1.5.3.105.1;
  }

  smiv2:alias msanAtm {
    smiv2:oid 1.3.6.1.4.1.1332.1.1.5.3.106;
  }

  smiv2:alias msanAtmGlobal {
    smiv2:oid 1.3.6.1.4.1.1332.1.1.5.3.106.1;
  }

  smiv2:alias msanEnergyMeter {
    smiv2:oid 1.3.6.1.4.1.1332.1.1.5.3.107;
  }

  smiv2:alias msanEnergyMeterGlobal {
    smiv2:oid 1.3.6.1.4.1.1332.1.1.5.3.107.1;
  }

  smiv2:alias msanArpInspection {
    smiv2:oid 1.3.6.1.4.1.1332.1.1.5.3.108;
  }

  smiv2:alias msanArpInspectionGlobal {
    smiv2:oid 1.3.6.1.4.1.1332.1.1.5.3.108.1;
  }

  smiv2:alias msanIsa {
    smiv2:oid 1.3.6.1.4.1.1332.1.1.5.3.109;
  }

  smiv2:alias msanIsaGlobal {
    smiv2:oid 1.3.6.1.4.1.1332.1.1.5.3.109.1;
  }

  smiv2:alias msanIsaStatistics {
    smiv2:oid 1.3.6.1.4.1.1332.1.1.5.3.109.2;
  }

  smiv2:alias msanSync {
    smiv2:oid 1.3.6.1.4.1.1332.1.1.5.3.110;
  }

  smiv2:alias msanSyncGlobal {
    smiv2:oid 1.3.6.1.4.1.1332.1.1.5.3.110.1;
  }

  smiv2:alias msanOnu {
    smiv2:oid 1.3.6.1.4.1.1332.1.1.5.3.111;
  }

  smiv2:alias msanOnuGlobal {
    smiv2:oid 1.3.6.1.4.1.1332.1.1.5.3.111.1;
  }

  smiv2:alias msanOlt {
    smiv2:oid 1.3.6.1.4.1.1332.1.1.5.3.112;
  }

  smiv2:alias msanOltGlobal {
    smiv2:oid 1.3.6.1.4.1.1332.1.1.5.3.112.1;
  }

  smiv2:alias msanTacacsServer {
    smiv2:oid 1.3.6.1.4.1.1332.1.1.5.3.113;
  }

  smiv2:alias msanTacacsServerGlobal {
    smiv2:oid 1.3.6.1.4.1.1332.1.1.5.3.113.1;
  }
    rpc saveConfig {
        description "Save running configuration to NVRAM.";
    }
    rpc clearConfig {
        description "Clear running configuration to default values.";
    }
    rpc reloadSystem {
        description "Reload the system.";
    }
    rpc systemSwUpgrade {
        description "Start system SW upgrade procedure.";
        input                               {


      leaf msanSystemSwUpgradeServerIpAddressType {
        type inet-address:InetAddressType;
        description
         "Specifies the type of the upgrade server address: ipv4[1], ipv6[2].";
        smiv2:defval ipv4;
        smiv2:max-access read-write;
        smiv2:oid 1.3.6.1.4.1.1332.1.1.5.3.1.10.3;
      }

      leaf msanSystemSwUpgradeServerIpAddress {
        type inet-address:InetAddress;
        description
         "The remote SW upgrade server IP address.";
        smiv2:max-access read-write;
        smiv2:oid 1.3.6.1.4.1.1332.1.1.5.3.1.10.4;
      }

      leaf msanSystemSwUpgradeServerDnsName {
        type rfc1213-mib:DisplayString;
        description
         "The remote SW upgrade server dns name.";
        smiv2:defval "";
        smiv2:max-access read-write;
        smiv2:oid 1.3.6.1.4.1.1332.1.1.5.3.1.10.5;
      }

      leaf msanSystemSwUpgradeProtocol {
        type enumeration {
          enum tftp {
            value 1;
          }
          enum ftp {
            value 2;
          }
          enum sftp {
            value 3;
          }
                    enum http {
                        value 4;
                    }
                    enum https {
                        value 5;
                    }

        }
        description
         "The SW upgrade protocol.";
        smiv2:defval tftp;
        smiv2:max-access read-write;
        smiv2:oid 1.3.6.1.4.1.1332.1.1.5.3.1.10.6;
      }

      leaf msanSystemSwUpgradeProtocolPortId {
        type int32 {
          range "-1..65535";
        }
        description
         "The SW upgrade protocol port number.
          If value is set to -1, standard protocol number is used.";
        smiv2:defval -1;
        smiv2:max-access read-write;
        smiv2:oid 1.3.6.1.4.1.1332.1.1.5.3.1.10.7;
      }

      leaf msanSystemSwUpgradeUserName {
        type rfc1213-mib:DisplayString;
        description
         "The username used in SW upgrade protocol.
          
          When sftp upgrade protocol is used, username must be set.";
        smiv2:defval "";
        smiv2:max-access read-write;
        smiv2:oid 1.3.6.1.4.1.1332.1.1.5.3.1.10.8;
      }

      leaf msanSystemSwUpgradeUserPassword {
        type rfc1213-mib:DisplayString;
        description
         "The user password used in SW upgrade protocol.
          
          When sftp upgrade protocol is used, username must be set.";
        smiv2:defval "";
        smiv2:max-access read-write;
        smiv2:oid 1.3.6.1.4.1.1332.1.1.5.3.1.10.9;
      }

      leaf msanSystemSwUpgradePath {
        type rfc1213-mib:DisplayString;
        description
         "The path to the SW package location.";
        smiv2:defval "";
        smiv2:max-access read-write;
        smiv2:oid 1.3.6.1.4.1.1332.1.1.5.3.1.10.10;
      }

      leaf msanSystemSwUpgradePackageName {
        type rfc1213-mib:DisplayString;
        description
         "The SW package name";
        smiv2:defval "";
        smiv2:max-access read-write;
        smiv2:oid 1.3.6.1.4.1.1332.1.1.5.3.1.10.11;
      }        }
    }


}
